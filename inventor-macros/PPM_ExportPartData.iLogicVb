' PPM_ExportPartData.iLogicVb
' Exports a structured Excel BOM with all PPM data from the active assembly.
' Four sheets: PARTS, ASSEMBLIES, REPORT, BOM_FLAT
' Assembly walk: ThisApplication.Documents + CollectReferencedPaths (crash-safe)
' xlsx: ZIP+XML via System.IO.Compression — no OLEDB dependency

AddReference "System.Drawing"
AddReference "System.Windows.Forms"
AddReference "System.Xml"
AddReference "System.IO.Compression"
AddReference "System.IO.Compression.FileSystem"

Sub Main()
    ' Main() MUST be parameterless -- confirmed by a real iLogic compile
    ' error ("The rule must contain: Sub Main() ... End Sub") when this
    ' was first tried with Optional parameters directly on Main.
    '
    ' Real fix, confirmed via official Autodesk documentation
    ' (RunExternalRule / NameValueMap arguments, and the RuleArguments
    ' object available inside any rule): Main() stays parameterless, but
    ' reads incoming values from RuleArguments if present. A future
    ' orchestrator calls this rule like:
    '   Dim oArgs As Inventor.NameValueMap = _
    '       ThisApplication.TransientObjects.CreateNameValueMap()
    '   oArgs.Add("JobPackageMode", True)
    '   oArgs.Add("JobPackageDestPath", somePath)
    '   iLogicVb.RunExternalRule("PPM_ExportPartData", oArgs)
    ' Normal invocation (ribbon/Rules panel double-click) passes no
    ' arguments, RuleArguments.Exists(...) is False for both, and
    ' behavior is completely unchanged from the original.
    ' NOT YET LIVE-TESTED -- RuleArguments/RunExternalRule are real,
    ' documented API, but this exact usage hasn't been run in Inventor
    ' yet. Confirm with a real cross-rule test before trusting it in
    ' the orchestrator (step 4).
    Dim jpMode As Boolean = False
    Dim jpPath As String = ""
    Try
        If RuleArguments.Exists("JobPackageMode") Then
            jpMode = CBool(RuleArguments("JobPackageMode"))
        End If
        If RuleArguments.Exists("JobPackageDestPath") Then
            jpPath = CStr(RuleArguments("JobPackageDestPath"))
        End If
    Catch
        ' RuleArguments unavailable/empty on a normal, argument-less
        ' invocation -- fall through with the defaults above, same as
        ' original behavior.
    End Try
    DoExport(jpMode, jpPath)
End Sub

Sub DoExport(Optional JobPackageMode As Boolean = False, _
        Optional JobPackageDestPath As String = "")
    ' JobPackageMode / JobPackageDestPath -- NEW (D-681 step 2). Both
    ' default to the exact original standalone behavior (interactive
    ' destination dialog, all 4 sheets including REPORT) when called
    ' with no arguments, as it always has been. Intended to be called
    ' together by the future PPM_SendToEstimator orchestrator (step 4,
    ' not yet built): JobPackageMode=True suppresses the REPORT sheet
    ' (3 sheets only: PARTS, ASSEMBLIES, BOM_FLAT, per D-328).
    ' JobPackageDestPath, when non-empty, is treated as the FULL target
    ' .xlsx file path and skips the interactive destination dialog
    ' entirely -- deliberately NOT done via SendKeys (unlike the Weld
    ' Bead Report step, D-329) since this dialog is our own code, not a
    ' native Inventor command; bypassing it directly is more robust than
    ' faking keystrokes into it. Parent folder is created if missing
    ' (the orchestrator's bom/ subfolder may not exist yet).
    ' NOTE: the actual cross-rule invocation mechanism for calling THIS
    ' sub (not Main) with real argument values from another iLogic rule
    ' is NOT YET CONFIRMED -- Main()'s own parameterless requirement
    ' means the orchestrator can't just call "PPM_ExportPartData" the
    ' normal way and expect these values to apply. This needs its own
    ' confirmed solution as part of step 4 (candidates: iLogic Shared
    ' Modules so DoExport can be called directly cross-rule, or a small
    ' temp flag-file handoff matching the existing "last folder" file
    ' pattern already used lower in this same file). Genuinely unresolved
    ' -- do not assume either approach works without testing it first.

    ' ── Auto-update check ────────────────────────────────────────
    Dim localPath   As String = "C:\PPM Cuts and Bends\iLogic\PPM_ExportPartData.iLogicVb"
    Dim networkPath As String = "X:\USER\Gavrilović\iLogic\PPM_ExportPartData.iLogicVb"
    Try
        If System.IO.File.Exists(networkPath) AndAlso System.IO.File.Exists(localPath) Then
            Dim netTime   As DateTime = System.IO.File.GetLastWriteTime(networkPath)
            Dim localTime As DateTime = System.IO.File.GetLastWriteTime(localPath)
            If netTime > localTime Then
                System.IO.File.Copy(networkPath, localPath, True)
                System.Windows.Forms.MessageBox.Show( _
                    "Nova verzija je instalirana." & vbCrLf & _
                    "New version installed." & vbCrLf & vbCrLf & _
                    "Pokrenite makro ponovo." & vbCrLf & _
                    "Please run the macro again.", _
                    "PPM - Azuriranje / Update", _
                    System.Windows.Forms.MessageBoxButtons.OK, _
                    System.Windows.Forms.MessageBoxIcon.Information)
                Exit Sub
            End If
        End If
    Catch : End Try
    ' ─────────────────────────────────────────────────────────────

    ' ── Palette (D-258) ──────────────────────────────────────────
    Dim cBg      As System.Drawing.Color = System.Drawing.Color.FromArgb(59, 68, 83)
    Dim cSurface As System.Drawing.Color = System.Drawing.Color.FromArgb(72, 82, 98)
    Dim cAccent  As System.Drawing.Color = System.Drawing.Color.FromArgb(46, 125, 209)
    Dim cText    As System.Drawing.Color = System.Drawing.Color.FromArgb(230, 237, 243)
    Dim cSub     As System.Drawing.Color = System.Drawing.Color.FromArgb(180, 190, 200)
    Dim cGreen   As System.Drawing.Color = System.Drawing.Color.FromArgb(63, 185, 80)
    Dim cAmber   As System.Drawing.Color = System.Drawing.Color.FromArgb(210, 153, 34)
    Dim cInput   As System.Drawing.Color = System.Drawing.Color.FromArgb(33, 38, 45)

    Dim fUI   As New System.Drawing.Font("Segoe UI", 9)
    Dim fSub  As New System.Drawing.Font("Segoe UI", 8)
    Dim fBold As New System.Drawing.Font("Segoe UI", 9, System.Drawing.FontStyle.Bold)
    Dim fMono As New System.Drawing.Font("Consolas", 10, System.Drawing.FontStyle.Bold)

    ' ── Guard: assembly only ──────────────────────────────────────
    If Not TypeOf ThisApplication.ActiveDocument Is AssemblyDocument Then
        ShowError("Otvori sklop (.iam) pre pokretanja makroa." & vbCrLf & _
                  "Open an assembly (.iam) before running this macro.")
        GoTo Cleanup
    End If

    Dim oAsmDoc As AssemblyDocument = CType(ThisApplication.ActiveDocument, AssemblyDocument)
    Dim asmPath As String = oAsmDoc.FullFileName
    Dim asmName As String = System.IO.Path.GetFileNameWithoutExtension(asmPath)

    ' ── Load org config ───────────────────────────────────────────
    Const ORG_CONFIG_PATH As String = _
        "X:\USER\Gavrilović\iLogic\config\ppm_operations_config.json"

    If Not System.IO.File.Exists(ORG_CONFIG_PATH) Then
        ShowError("Pokrenite PPM Operations Setup prvo." & vbCrLf & _
                  "Run PPM Operations Setup first." & vbCrLf & vbCrLf & ORG_CONFIG_PATH)
        GoTo Cleanup
    End If

    Dim orgOps As New System.Collections.Generic.List(Of String())
    Try
        Dim raw As String = System.IO.File.ReadAllText( _
            ORG_CONFIG_PATH, System.Text.Encoding.UTF8)
        ParseOrgOps(raw, orgOps)
    Catch ex As Exception
        ShowError("Greška pri čitanju org konfiguracije:" & vbCrLf & _
                  "Error reading org config:" & vbCrLf & vbCrLf & ex.Message)
        GoTo Cleanup
    End Try

    If orgOps.Count = 0 Then
        ShowError("Org konfiguracija je prazna. Pokrenite PPM Operations Setup." & vbCrLf & _
                  "Org config is empty. Run PPM Operations Setup.")
        GoTo Cleanup
    End If

    ' ── Pre-scan: collect referenced paths ───────────────────────
    ' CollectReferencedPaths walks ReferencedDocuments recursively —
    ' never touches ComponentOccurrences (crash-safe on broken cross-refs).
    Dim asmRefPaths As New System.Collections.Generic.HashSet(Of String)( _
        System.StringComparer.OrdinalIgnoreCase)
    Try
        CollectReferencedPaths(oAsmDoc, asmRefPaths)
    Catch : End Try

    Dim preScanParts As Integer = 0
    Dim preScanAsms  As Integer = 0

    For Each oDoc As Document In ThisApplication.Documents
        Dim docPath As String = ""
        Try : docPath = oDoc.FullFileName : Catch : Continue For : End Try
        If Not asmRefPaths.Contains(docPath) Then Continue For
        If TypeOf oDoc Is PartDocument Then
            preScanParts += 1
        ElseIf TypeOf oDoc Is AssemblyDocument Then
            preScanAsms += 1
        End If
    Next

    ' ── Load last used folder ─────────────────────────────────────
    Dim lastPathFile As String = System.IO.Path.Combine( _
        System.IO.Path.GetTempPath(), "PPM_ExportPartData_LastFolder.txt")
    Dim lastFolder As String = ""
    Try
        If System.IO.File.Exists(lastPathFile) Then
            lastFolder = System.IO.File.ReadAllText(lastPathFile).Trim()
            If Not System.IO.Directory.Exists(lastFolder) Then lastFolder = ""
        End If
    Catch : End Try

    Dim destFolder As String = lastFolder
    Dim xlsxName   As String = asmName & "_PPM_BOM.xlsx"
    Dim xlsxPath As String

    If JobPackageDestPath <> "" Then
        ' ── Job Package mode: skip the interactive dialog entirely ──
        xlsxPath   = JobPackageDestPath
        destFolder = System.IO.Path.GetDirectoryName(xlsxPath)
        Try
            If Not System.IO.Directory.Exists(destFolder) Then
                System.IO.Directory.CreateDirectory(destFolder)
            End If
        Catch ex As Exception
            ShowError("Ne mogu da kreiram odredisni folder:" & vbCrLf & _
                      "Could not create destination folder:" & vbCrLf & vbCrLf & _
                      destFolder & vbCrLf & vbCrLf & ex.Message)
            GoTo Cleanup
        End Try
    Else
    ' ── Dialog ───────────────────────────────────────────────────
    Dim dlg As New System.Windows.Forms.Form
    dlg.Text            = "PPM - BOM Export"
    dlg.Size            = New System.Drawing.Size(560, 316)
    dlg.StartPosition   = System.Windows.Forms.FormStartPosition.CenterScreen
    dlg.FormBorderStyle = System.Windows.Forms.FormBorderStyle.FixedDialog
    dlg.MaximizeBox     = False : dlg.MinimizeBox = False
    dlg.BackColor       = cBg
    dlg.AutoScaleMode   = System.Windows.Forms.AutoScaleMode.None

    Dim lblTitle As New System.Windows.Forms.Label
    lblTitle.Text      = "PPM BOM EXPORT"
    lblTitle.Font      = New System.Drawing.Font("Segoe UI", 10, _
        System.Drawing.FontStyle.Bold)
    lblTitle.ForeColor = cAccent
    lblTitle.Location  = New System.Drawing.Point(20, 18)
    lblTitle.Size      = New System.Drawing.Size(520, 22)
    dlg.Controls.Add(lblTitle)

    Dim lblAsm As New System.Windows.Forms.Label
    lblAsm.Text      = asmName
    lblAsm.Font      = fMono
    lblAsm.ForeColor = cGreen
    lblAsm.Location  = New System.Drawing.Point(20, 44)
    lblAsm.Size      = New System.Drawing.Size(520, 20)
    dlg.Controls.Add(lblAsm)

    Dim lblInfo As New System.Windows.Forms.Label
    lblInfo.Text      = preScanParts & " delova / " & preScanParts & " parts,   " & _
                        preScanAsms  & " sklopova / " & preScanAsms & " assemblies"
    lblInfo.Font      = fSub
    lblInfo.ForeColor = cSub
    lblInfo.Location  = New System.Drawing.Point(20, 68)
    lblInfo.Size      = New System.Drawing.Size(520, 18)
    dlg.Controls.Add(lblInfo)

    Dim sep1 As New System.Windows.Forms.Label
    sep1.BackColor = cSurface
    sep1.Location  = New System.Drawing.Point(20, 96)
    sep1.Size      = New System.Drawing.Size(520, 1)
    dlg.Controls.Add(sep1)

    Dim lblFolder As New System.Windows.Forms.Label
    lblFolder.Text      = "Odredisni folder / Destination folder:"
    lblFolder.Font      = fUI : lblFolder.ForeColor = cSub
    lblFolder.Location  = New System.Drawing.Point(20, 108)
    lblFolder.Size      = New System.Drawing.Size(300, 18)
    dlg.Controls.Add(lblFolder)

    Dim txtFolder As New System.Windows.Forms.TextBox
    txtFolder.Font      = fSub
    txtFolder.BackColor = cInput
    txtFolder.ForeColor = If(destFolder <> "", cGreen, cSub)
    txtFolder.Text      = If(destFolder <> "", destFolder, "(nije izabran / not selected)")
    txtFolder.Location  = New System.Drawing.Point(20, 128)
    txtFolder.Size      = New System.Drawing.Size(392, 22)
    dlg.Controls.Add(txtFolder)

    Dim btnBrowse As New System.Windows.Forms.Button
    btnBrowse.Text      = "..."
    btnBrowse.Font      = fBold
    btnBrowse.BackColor = cSurface : btnBrowse.ForeColor = cText
    btnBrowse.FlatStyle = System.Windows.Forms.FlatStyle.Flat
    btnBrowse.FlatAppearance.BorderColor = cAccent
    btnBrowse.Location  = New System.Drawing.Point(420, 127)
    btnBrowse.Size      = New System.Drawing.Size(120, 24)
    dlg.Controls.Add(btnBrowse)

    Dim lblFile As New System.Windows.Forms.Label
    lblFile.Text      = "Ime fajla / File name:"
    lblFile.Font      = fUI : lblFile.ForeColor = cSub
    lblFile.Location  = New System.Drawing.Point(20, 162)
    lblFile.Size      = New System.Drawing.Size(300, 18)
    dlg.Controls.Add(lblFile)

    Dim txtFile As New System.Windows.Forms.TextBox
    txtFile.Font      = fSub
    txtFile.BackColor = cInput
    txtFile.ForeColor = cText
    txtFile.Text      = xlsxName
    txtFile.Location  = New System.Drawing.Point(20, 182)
    txtFile.Size      = New System.Drawing.Size(520, 22)
    dlg.Controls.Add(txtFile)

    Dim sep2 As New System.Windows.Forms.Label
    sep2.BackColor = cSurface
    sep2.Location  = New System.Drawing.Point(20, 220)
    sep2.Size      = New System.Drawing.Size(520, 1)
    dlg.Controls.Add(sep2)

    Dim btnCancel As New System.Windows.Forms.Button
    btnCancel.Text      = "Odustani / Cancel"
    btnCancel.Font      = fUI
    btnCancel.BackColor = cSurface : btnCancel.ForeColor = cSub
    btnCancel.FlatStyle = System.Windows.Forms.FlatStyle.Flat
    btnCancel.FlatAppearance.BorderColor = cSurface
    btnCancel.Location     = New System.Drawing.Point(180, 238)
    btnCancel.Size         = New System.Drawing.Size(150, 34)
    btnCancel.DialogResult = System.Windows.Forms.DialogResult.Cancel
    dlg.Controls.Add(btnCancel)

    Dim btnConfirm As New System.Windows.Forms.Button
    btnConfirm.Text      = "Potvrdi / Confirm"
    btnConfirm.Font      = fBold
    btnConfirm.BackColor = cAccent : btnConfirm.ForeColor = cText
    btnConfirm.FlatStyle = System.Windows.Forms.FlatStyle.Flat
    btnConfirm.FlatAppearance.BorderColor = cAccent
    btnConfirm.Location     = New System.Drawing.Point(370, 238)
    btnConfirm.Size         = New System.Drawing.Size(170, 34)
    btnConfirm.DialogResult = System.Windows.Forms.DialogResult.OK
    btnConfirm.Enabled      = (destFolder <> "")
    dlg.Controls.Add(btnConfirm)

    dlg.AcceptButton = btnConfirm
    dlg.CancelButton = btnCancel

    AddHandler btnBrowse.Click, Sub(s, e)
        Dim fbd As New System.Windows.Forms.FolderBrowserDialog
        fbd.Description = "Izaberi odredisni folder / Select destination folder"
        Dim typed As String = txtFolder.Text.Trim()
        If System.IO.Directory.Exists(typed) Then
            fbd.SelectedPath = typed
        ElseIf lastFolder <> "" Then
            fbd.SelectedPath = lastFolder
        End If
        If fbd.ShowDialog() = System.Windows.Forms.DialogResult.OK Then
            destFolder          = fbd.SelectedPath
            txtFolder.Text      = destFolder
            txtFolder.ForeColor = cGreen
            btnConfirm.Enabled  = True
        End If
    End Sub

    AddHandler txtFolder.TextChanged, Sub(s, e)
        Dim typed As String = txtFolder.Text.Trim()
        If System.IO.Directory.Exists(typed) Then
            destFolder          = typed
            txtFolder.ForeColor = cGreen
            btnConfirm.Enabled  = True
        Else
            btnConfirm.Enabled = False
        End If
    End Sub

    dlg.ShowDialog()
    If dlg.DialogResult <> System.Windows.Forms.DialogResult.OK Then GoTo Cleanup

    destFolder = txtFolder.Text.Trim()
    xlsxName   = txtFile.Text.Trim()
    If xlsxName = ""                            Then xlsxName = asmName & "_PPM_BOM.xlsx"
    If Not xlsxName.ToLower().EndsWith(".xlsx") Then xlsxName &= ".xlsx"

    If Not System.IO.Directory.Exists(destFolder) Then
        ShowError("Odredisni folder ne postoji." & vbCrLf & _
                  "Destination folder does not exist.")
        GoTo Cleanup
    End If

    Try : System.IO.File.WriteAllText(lastPathFile, destFolder) : Catch : End Try

    xlsxPath = System.IO.Path.Combine(destFolder, xlsxName)
    End If

    ' ════════════════════════════════════════════════════════════════
    ' PART 1 END — commit checkpoint
    ' Part 2: assembly walk, iProperty reads, xlsx sheets 1-2
    ' ════════════════════════════════════════════════════════════════

    ' ── Parse structured BOM (primary data skeleton) ─────────────
    Dim bomRows As System.Collections.Generic.List(Of Object()) = _
        ParseStructuredBom(oAsmDoc, asmName)

    ' ── Detect PurchasedUnit assemblies (OQ-205 / D-703) ──────────
    ' FIXED after a live test: the first version of this detection was
    ' gated on ThisApplication.Documents (inside the enrichMap loop
    ' below), which returned purchasedPns=0 even for a document
    ' confirmed correctly flagged and excluded by the SIBLING macro
    ' (PPM_BatchExportFlatPatterns). Root cause: ThisApplication.Documents
    ' only reliably contains documents Inventor is tracking as currently
    ' "open" top-level documents -- for a large/deep assembly this does
    ' not reliably include every referenced subassembly. Fixed by
    ' switching to the SAME reliable mechanism already confirmed working
    ' in PPM_BatchExportFlatPatterns' CollectReferencedPaths: a direct
    ' recursive walk of .ReferencedDocuments, independent of whatever
    ' ThisApplication.Documents happens to contain.
    Dim purchasedPns As New System.Collections.Generic.HashSet(Of String)( _
        System.StringComparer.OrdinalIgnoreCase)
    Try
        CollectPurchasedPns(oAsmDoc, purchasedPns)
    Catch
    End Try

    ' ── Build enrichment map: pn → {docType, material, thickMM,
    '    bendCount, ppmHoles, ppmThreads, opFlags} from open docs
    Dim enrichMap As New System.Collections.Generic.Dictionary(Of String, Object())( _
        System.StringComparer.OrdinalIgnoreCase)
    Dim seenEnrich As New System.Collections.Generic.HashSet(Of String)( _
        System.StringComparer.OrdinalIgnoreCase)
    For Each oDoc As Document In ThisApplication.Documents
        Dim docPath As String = ""
        Try : docPath = oDoc.FullFileName : Catch : Continue For : End Try
        If Not asmRefPaths.Contains(docPath) Then Continue For
        Dim ePn As String = ReadDTP(oDoc, "Part Number")
        If ePn = "" Then
            Try : ePn = System.IO.Path.GetFileNameWithoutExtension(docPath) : Catch : End Try
        End If
        If ePn = "" OrElse seenEnrich.Contains(ePn) Then Continue For
        seenEnrich.Add(ePn)
        Dim eOpFlags As New System.Collections.Generic.Dictionary(Of String, Integer)( _
            System.StringComparer.OrdinalIgnoreCase)
        For Each op As String() In orgOps
            Dim flagVal As Integer = 0
            Try : flagVal = CInt(ReadCustomProp(oDoc, "PPM_" & op(0).Replace("-", "_"))) : Catch : End Try
            eOpFlags(op(0)) = flagVal
        Next
        If TypeOf oDoc Is PartDocument Then
            Dim oPart As PartDocument = CType(oDoc, PartDocument)
            Dim material  As String  = ""
            Dim thickMM   As Double  = 0
            Dim bendCount As Integer = 0
            Try : material = oPart.ComponentDefinition.Material.Name : Catch : End Try
            If TypeOf oPart.ComponentDefinition Is SheetMetalComponentDefinition Then
                Dim oSM As SheetMetalComponentDefinition = _
                    CType(oPart.ComponentDefinition, SheetMetalComponentDefinition)
                Try : thickMM = oSM.Thickness.ModelValue * 10 : Catch : End Try
                bendCount = GetBendCount(oSM, oDoc)
            End If
            enrichMap(ePn) = New Object() {"Part", material, thickMM, bendCount, _
                ReadCustomProp(oDoc, "PPM_Holes"), ReadCustomProp(oDoc, "PPM_Threads"), eOpFlags}
        ElseIf TypeOf oDoc Is AssemblyDocument Then
            Dim eDocType As String = "Mech Assy"
            Try
                If TypeOf CType(oDoc, AssemblyDocument).ComponentDefinition _
                    Is WeldmentComponentDefinition Then eDocType = "Weld Assy"
            Catch : End Try
            enrichMap(ePn) = New Object() {eDocType, "", 0.0, 0, "", "", eOpFlags}
        End If
    Next

    ' ── Filter out children of PurchasedUnit assemblies (OQ-205 / D-703) ──
    ' The purchased assembly's OWN row is kept (single costed line item,
    ' per explicit confirmation) -- only rows whose Item hierarchy string
    ' is a proper descendant (e.g. "9.1", "9.2.3" under purchased "9")
    ' are dropped. Inventor's native Structured BOM export has no
    ' knowledge of this custom property, so this has to be a post-parse
    ' filter rather than something the BOM export itself can be told to
    ' skip.
    If purchasedPns.Count > 0 Then
        Dim purchasedItemStrs As New System.Collections.Generic.List(Of String)
        For Each bRow As Object() In bomRows
            Dim rPn As String = CStr(bRow(2))
            If purchasedPns.Contains(rPn) Then
                purchasedItemStrs.Add(CStr(bRow(0)))
            End If
        Next

        Dim filteredRows As New System.Collections.Generic.List(Of Object())
        For Each bRow As Object() In bomRows
            Dim rItemStr As String = CStr(bRow(0))
            Dim isDescendant As Boolean = False
            For Each pItem As String In purchasedItemStrs
                If rItemStr.StartsWith(pItem & ".") Then
                    isDescendant = True
                    Exit For
                End If
            Next
            If Not isDescendant Then filteredRows.Add(bRow)
        Next
        bomRows = filteredRows
    End If

    ' ── Build partRows / asmRows from BOM + enrichment ───────────
    ' partRows: {level, pn, desc, qty, docType, material, thickMM,
    '            bendCount, ppmHoles, ppmThreads, opFlags, itemStr}
    ' asmRows:  {level, pn, desc, qty, docType, opFlags, itemStr}
    Dim partRows As New System.Collections.Generic.List(Of Object())
    Dim asmRows  As New System.Collections.Generic.List(Of Object())

    For Each bomRow As Object() In bomRows
        Dim itemStr   As String  = CStr(bomRow(0))
        Dim bLevel    As Integer = CInt(bomRow(1))
        Dim bPn       As String  = CStr(bomRow(2))
        Dim bDesc     As String  = CStr(bomRow(3))
        Dim bQty      As Integer = CInt(bomRow(4))
        Dim docType   As String  = "Part"
        Dim material  As String  = ""
        Dim thickMM   As Double  = 0.0
        Dim bendCount As Integer = 0
        Dim ppmHoles  As String  = ""
        Dim ppmThreads As String = ""
        Dim opFlags As New System.Collections.Generic.Dictionary(Of String, Integer)( _
            System.StringComparer.OrdinalIgnoreCase)
        If enrichMap.ContainsKey(bPn) Then
            Dim e As Object() = enrichMap(bPn)
            docType    = CStr(e(0))
            material   = CStr(e(1))
            thickMM    = CDbl(e(2))
            bendCount  = CInt(e(3))
            ppmHoles   = CStr(e(4))
            ppmThreads = CStr(e(5))
            opFlags    = CType(e(6), System.Collections.Generic.Dictionary(Of String, Integer))
        End If
        If docType = "Part" Then
            partRows.Add(New Object() {bLevel, bPn, bDesc, bQty, docType, material, _
                thickMM, bendCount, ppmHoles, ppmThreads, opFlags, itemStr})
        Else
            asmRows.Add(New Object() {bLevel, bPn, bDesc, bQty, docType, opFlags, itemStr})
        End If
    Next

    If partRows.Count = 0 AndAlso asmRows.Count = 0 Then
        ShowError("Nisu pronađeni delovi ni sklopovi u aktivnom sklopu." & vbCrLf & _
                  "No parts or assemblies found in the active assembly.")
        GoTo Cleanup
    End If

    ' ── Write xlsx ───────────────────────────────────────────────
    If System.IO.File.Exists(xlsxPath) Then
        Try : System.IO.File.Delete(xlsxPath) : Catch : End Try
    End If
    Try
        WriteXlsx(xlsxPath, asmName, orgOps, partRows, asmRows, JobPackageMode)
    Catch ex As Exception
        ShowError("Greška pri pisanju xlsx fajla:" & vbCrLf & _
                  "Error writing xlsx file:" & vbCrLf & vbCrLf & _
                  "bomRows=" & bomRows.Count & " partRows=" & partRows.Count & _
                  " asmRows=" & asmRows.Count & " purchasedPns=" & purchasedPns.Count & vbCrLf & vbCrLf & _
                  ex.ToString())
        GoTo Cleanup
    End Try

    ' ════════════════════════════════════════════════════════════════
    ' PART 2 END — commit checkpoint
    ' Part 3: sheets 3-4, summary dialog
    ' ════════════════════════════════════════════════════════════════

    ShowSummaryDialog(partRows.Count, asmRows.Count, xlsxPath, _
        New System.Collections.Generic.List(Of String)(purchasedPns))

Cleanup:
    fUI.Dispose() : fSub.Dispose() : fBold.Dispose() : fMono.Dispose()

End Sub

' ════════════════════════════════════════════════════════════════════
' SUBROUTINES — Part 1
' ════════════════════════════════════════════════════════════════════

Sub CollectReferencedPaths(oDoc As Document, _
        ByRef paths As System.Collections.Generic.HashSet(Of String))
    For Each refDoc As Document In oDoc.ReferencedDocuments
        Dim refPath As String = ""
        Try : refPath = refDoc.FullFileName : Catch : Continue For : End Try
        If refPath = "" OrElse paths.Contains(refPath) Then Continue For
        paths.Add(refPath)
        If TypeOf refDoc Is AssemblyDocument Then
            CollectReferencedPaths(refDoc, paths)
        End If
    Next
End Sub

Sub CollectPurchasedPns(oDoc As Document, _
        ByRef purchasedPns As System.Collections.Generic.HashSet(Of String))
    ' NEW (OQ-205 / D-703, fixed after live test): recursively walk
    ' .ReferencedDocuments directly -- same reliable mechanism already
    ' confirmed working in PPM_BatchExportFlatPatterns' CollectReferencedPaths
    ' -- rather than relying on ThisApplication.Documents, which does not
    ' reliably include every referenced subassembly for a large tree.
    ' Does NOT recurse into a PurchasedUnit assembly's own children
    ' (matches D-703 / the sibling macro's behavior -- what's inside a
    ' purchased unit is irrelevant either way, since D-703 already
    ' excludes it from the BOM).
    For Each refDoc As Document In oDoc.ReferencedDocuments
        If TypeOf refDoc Is AssemblyDocument Then
            Dim isPurchased As Boolean = False
            Try
                Dim propVal = refDoc.PropertySets.Item("Inventor User Defined Properties") _
                    .Item("PPM_SubassemblyTreatment").Value.ToString()
                isPurchased = (propVal = "PurchasedUnit")
            Catch
            End Try
            If isPurchased Then
                Dim rPn As String = ReadDTP(refDoc, "Part Number")
                If rPn = "" Then
                    Try : rPn = System.IO.Path.GetFileNameWithoutExtension(refDoc.FullFileName) : Catch : End Try
                End If
                If rPn <> "" Then purchasedPns.Add(rPn)
            Else
                CollectPurchasedPns(refDoc, purchasedPns)
            End If
        End If
    Next
End Sub

Sub ParseOrgOps(content As String, _
        ByRef ops As System.Collections.Generic.List(Of String()))
    Dim parts() As String = content.Split( _
        New String() {"""id"""}, StringSplitOptions.RemoveEmptyEntries)
    For i As Integer = 1 To parts.Length - 1
        Dim seg As String = parts(i)
        Dim id  As String = ExtractFirstQuotedValue(seg)
        Dim nm  As String = ExtractJsonField(seg, "name")
        Dim cat As String = ExtractJsonField(seg, "category")
        If id.StartsWith("OP-") AndAlso nm <> "" Then
            ops.Add(New String() {id, nm, cat})
        End If
    Next
End Sub

Function ExtractFirstQuotedValue(s As String) As String
    Dim ci As Integer = s.IndexOf(":")
    If ci < 0 Then Return ""
    Dim q1 As Integer = s.IndexOf("""", ci)
    If q1 < 0 Then Return ""
    Dim q2 As Integer = s.IndexOf("""", q1 + 1)
    If q2 < 0 Then Return ""
    Return s.Substring(q1 + 1, q2 - q1 - 1)
End Function

Function ExtractJsonField(block As String, fieldName As String) As String
    Dim key As String = """" & fieldName & """"
    Dim ki  As Integer = block.IndexOf(key)
    If ki < 0 Then Return ""
    Dim ci  As Integer = block.IndexOf(":", ki + key.Length)
    If ci < 0 Then Return ""
    Dim q1  As Integer = block.IndexOf("""", ci + 1)
    If q1 < 0 Then Return ""
    Dim q2  As Integer = block.IndexOf("""", q1 + 1)
    If q2 < 0 Then Return ""
    Return block.Substring(q1 + 1, q2 - q1 - 1)
End Function

Sub ShowError(msg As String)
    ' FIXED: previously used a fixed-size Label (420x80) inside a fixed
    ' 460x200 Form -- any message longer than that was SILENTLY CLIPPED,
    ' invisible, not truncated-with-ellipsis. This is why a real
    ' diagnostic error (row counts + full ex.ToString()) only ever showed
    ' the row counts -- the exception detail was there in the string,
    ' just never rendered. Now uses a resizable form with a scrollable,
    ' word-wrapped, read-only, SELECTABLE multi-line textbox (so the
    ' text can be copied out for reporting) instead.
    Dim ef As New System.Windows.Forms.Form
    ef.Text            = "PPM - Greška / Error"
    ef.Size            = New System.Drawing.Size(620, 420)
    ef.StartPosition   = System.Windows.Forms.FormStartPosition.CenterScreen
    ef.FormBorderStyle = System.Windows.Forms.FormBorderStyle.Sizable
    ef.MinimumSize     = New System.Drawing.Size(400, 250)
    ef.BackColor       = System.Drawing.Color.FromArgb(59, 68, 83)
    ef.MaximizeBox     = True : ef.AutoScaleMode = System.Windows.Forms.AutoScaleMode.None

    Dim txt As New System.Windows.Forms.TextBox
    txt.Text        = msg
    txt.Multiline   = True
    txt.ReadOnly    = True
    txt.ScrollBars  = System.Windows.Forms.ScrollBars.Vertical
    txt.WordWrap    = True
    txt.Font        = New System.Drawing.Font("Segoe UI", 9)
    txt.ForeColor   = System.Drawing.Color.FromArgb(210, 153, 34)
    txt.BackColor   = System.Drawing.Color.FromArgb(45, 52, 64)
    txt.BorderStyle = System.Windows.Forms.BorderStyle.FixedSingle
    txt.Location    = New System.Drawing.Point(15, 15)
    txt.Size        = New System.Drawing.Size(575, 320)
    txt.Anchor      = System.Windows.Forms.AnchorStyles.Top Or System.Windows.Forms.AnchorStyles.Bottom Or _
                       System.Windows.Forms.AnchorStyles.Left Or System.Windows.Forms.AnchorStyles.Right
    ef.Controls.Add(txt)

    Dim btn As New System.Windows.Forms.Button
    btn.Text      = "OK"
    btn.Font      = New System.Drawing.Font("Segoe UI", 9, System.Drawing.FontStyle.Bold)
    btn.BackColor = System.Drawing.Color.FromArgb(46, 125, 209)
    btn.ForeColor = System.Drawing.Color.FromArgb(230, 237, 243)
    btn.FlatStyle = System.Windows.Forms.FlatStyle.Flat
    btn.FlatAppearance.BorderColor = System.Drawing.Color.FromArgb(46, 125, 209)
    btn.Location     = New System.Drawing.Point(495, 345)
    btn.Size         = New System.Drawing.Size(95, 32)
    btn.Anchor       = System.Windows.Forms.AnchorStyles.Bottom Or System.Windows.Forms.AnchorStyles.Right
    btn.DialogResult = System.Windows.Forms.DialogResult.OK
    ef.Controls.Add(btn) : ef.AcceptButton = btn : ef.ShowDialog()
End Sub

' ════════════════════════════════════════════════════════════════
' Part 2 Helpers — property reads, bend detection, xlsx write
' ════════════════════════════════════════════════════════════════

Function ReadDTP(oDoc As Document, propName As String) As String
    Try
        Return CStr(oDoc.PropertySets.Item("Design Tracking Properties"). _
            Item(propName).Value).Trim()
    Catch : Return "" : End Try
End Function

Function ReadCustomProp(oDoc As Document, propName As String) As String
    Try
        Return CStr(oDoc.PropertySets.Item("Inventor User Defined Properties"). _
            Item(propName).Value).Trim()
    Catch : Return "" : End Try
End Function

Function GetBendCount(oSM As SheetMetalComponentDefinition, oDoc As Document) As Integer
    Dim n As Integer = 0
    Try
        For Each feat As Object In oSM.Features
            Try
                If InStr(LCase(feat.Type.ToString()), "bend") > 0 Then n += 1
            Catch : End Try
        Next
    Catch : End Try
    If n > 0 Then Return n
    Try : n = CInt(oDoc.PropertySets.Item("Design Tracking Properties"). _
        Item("Bend Count").Value) : Catch : End Try
    If n > 0 Then Return n
    Dim hasFP As Boolean = False
    Try : hasFP = (oSM.FlatPattern IsNot Nothing) : Catch : End Try
    Dim thk As Double = 0
    Try : thk = oSM.Thickness.ModelValue : Catch : End Try
    If hasFP AndAlso thk > 0 Then Return 1
    Return 0
End Function

' Returns list of BOM rows: {itemStr, level, pn, desc, qty}
' Exports the [Structured] BOM view and reads it back with column-name matching.
Function ParseStructuredBom(oAsmDoc As AssemblyDocument, asmName As String) _
        As System.Collections.Generic.List(Of Object())
    Dim result As New System.Collections.Generic.List(Of Object())
    Dim bomDebugLines As New System.Collections.Generic.List(Of String)
    Try
        Dim oBOM As BOM = oAsmDoc.ComponentDefinition.BOM
        Try : oBOM.StructuredViewEnabled = True : Catch : End Try
        ' NEW (D-706): confirmed via official Autodesk BOM API
        ' documentation + a real working sample (BOMView_Export_Sample.htm)
        ' -- oBOM.StructuredViewFirstLevelOnly defaults to True, which
        ' silently limits the Structured view (and therefore this export)
        ' to only the assembly's DIRECT children, regardless of how deep
        ' the interactive BOM Editor's tree visually goes. This is the
        ' real, confirmed cause of a live test showing a nested
        ' subassembly's own children (multiple real levels deep, visible
        ' in Inventor's BOM Editor) completely absent from the exported
        ' BOM -- ground-truth-checked via the raw unmodified Inventor
        ' export (outlineLevel=0 on every row, flat Item numbers). Known
        ' edge case (Autodesk-documented): iAssemblies only support
        ' First-Level Structured view -- "All Levels" cannot be enabled
        ' for those regardless of this setting, so the Try/Catch below
        ' just lets that silently no-op rather than fail the whole export.
        Try : oBOM.StructuredViewFirstLevelOnly = False : Catch : End Try
        Dim oView As BOMView = Nothing
        Try : oView = oBOM.BOMViews.Item("Structured") : Catch : End Try
        If oView Is Nothing Then
            For Each v As BOMView In oBOM.BOMViews
                If v.Name.ToLower() <> "parts only" Then oView = v : Exit For
            Next
        End If
        If oView Is Nothing Then Return result

        Dim tmpPath As String = System.IO.Path.Combine( _
            System.IO.Path.GetTempPath(), asmName & "_PPM_StructBOM.xlsx")
        If System.IO.File.Exists(tmpPath) Then System.IO.File.Delete(tmpPath)
        oView.Export(tmpPath, kMicrosoftExcelFormat)
        If Not System.IO.File.Exists(tmpPath) Then Return result

        Using arc As System.IO.Compression.ZipArchive = _
            System.IO.Compression.ZipFile.Open(tmpPath, _
            System.IO.Compression.ZipArchiveMode.Read)

            Dim ss As New System.Collections.Generic.List(Of String)
            Dim ssEnt As System.IO.Compression.ZipArchiveEntry = arc.GetEntry("xl/sharedStrings.xml")
            If ssEnt IsNot Nothing Then
                Dim xd As New System.Xml.XmlDocument()
                Using st As System.IO.Stream = ssEnt.Open() : xd.Load(st) : End Using
                Dim mgr As New System.Xml.XmlNamespaceManager(xd.NameTable)
                mgr.AddNamespace("x", "http://schemas.openxmlformats.org/spreadsheetml/2006/main")
                For Each t As System.Xml.XmlNode In xd.SelectNodes("//x:t", mgr)
                    ss.Add(t.InnerText)
                Next
            End If

            Dim shEnt As System.IO.Compression.ZipArchiveEntry = arc.GetEntry("xl/worksheets/sheet1.xml")
            If shEnt Is Nothing Then Return result
            Dim xs As New System.Xml.XmlDocument()
            Using st As System.IO.Stream = shEnt.Open() : xs.Load(st) : End Using
            Dim xm As New System.Xml.XmlNamespaceManager(xs.NameTable)
            xm.AddNamespace("x", "http://schemas.openxmlformats.org/spreadsheetml/2006/main")

            Dim itemCol As Integer = -1, pnCol As Integer = -1
            Dim descCol As Integer = -1, qtyCol As Integer = -1
            Dim firstRow As Boolean = True

            For Each rowNode As System.Xml.XmlNode In xs.SelectNodes("//x:row", xm)
                Dim cellVals As New System.Collections.Generic.Dictionary(Of Integer, String)
                For Each c As System.Xml.XmlNode In rowNode.SelectNodes("x:c", xm)
                    Dim cn As Integer = GetCellColNum(c)
                    If cn < 0 Then Continue For
                    cellVals(cn) = GetCellValue(c, ss, xm)
                Next
                If firstRow Then
                    firstRow = False
                    For Each kv As System.Collections.Generic.KeyValuePair(Of Integer, String) _
                            In cellVals
                        Dim h As String = kv.Value.ToLower().Trim()
                        Select Case h
                            Case "item", "item number" : itemCol = kv.Key
                            Case "part number", "partnumber" : pnCol = kv.Key
                            Case "description" : descCol = kv.Key
                            Case "qty", "quantity" : qtyCol = kv.Key
                        End Select
                    Next
                Else
                    If itemCol < 0 Then Continue For
                    Dim itemStr As String = If(cellVals.ContainsKey(itemCol), cellVals(itemCol), "")
                    If itemStr = "" Then Continue For
                    Dim bPn   As String  = If(pnCol  >= 0 AndAlso cellVals.ContainsKey(pnCol),  cellVals(pnCol),  "")
                    Dim bDesc As String  = If(descCol >= 0 AndAlso cellVals.ContainsKey(descCol), cellVals(descCol), "")
                    Dim bQty  As Integer = 1
                    If qtyCol >= 0 AndAlso cellVals.ContainsKey(qtyCol) Then
                        Try : bQty = CInt(cellVals(qtyCol)) : Catch : End Try
                    End If
                    ' NEW (D-706 diagnostic): also read the row's real
                    ' outlineLevel attribute -- a standard OOXML row
                    ' attribute, confirmed real via Microsoft's own
                    ' documentation -- as a candidate MORE RELIABLE
                    ' source of hierarchy depth than counting dots in the
                    ' Item text, since a live test showed Item numbers can
                    ' be flat ("1","2","3") even for genuinely nested
                    ' assemblies, depending on this project's BOM Item
                    ' Numbering configuration in Inventor. Not yet used
                    ' for anything -- logged only, to see ground truth
                    ' before deciding whether it's actually populated by
                    ' Inventor's own BOMView.Export.
                    Dim rowOutlineLevel As Integer = 0
                    Try
                        Dim olAttr As System.Xml.XmlAttribute = rowNode.Attributes("outlineLevel")
                        If olAttr IsNot Nothing Then rowOutlineLevel = CInt(olAttr.Value)
                    Catch
                    End Try
                    bomDebugLines.Add("Item=""" & itemStr & """ outlineLevel=" & rowOutlineLevel & _
                        " PN=""" & bPn & """ rowXml=" & rowNode.OuterXml)

                    Dim dotCount As Integer = itemStr.Split("."c).Length - 1
                    result.Add(New Object() {itemStr, dotCount + 1, bPn, bDesc, bQty})
                End If
            Next
        End Using
        ' NEW (D-706 diagnostic): keep the raw temp file (was previously
        ' always deleted) and write the row-level debug dump next to it,
        ' so the actual native Inventor BOM export can be inspected
        ' directly instead of only trusting our re-parsed interpretation.
        Try
            Dim debugPath As String = tmpPath & "_debug.txt"
            System.IO.File.WriteAllText(debugPath, String.Join(vbCrLf, bomDebugLines))
        Catch
        End Try
    Catch : End Try
    Return result
End Function

Function GetCellColNum(c As System.Xml.XmlNode) As Integer
    Dim rAttr As System.Xml.XmlAttribute = c.Attributes("r")
    If rAttr Is Nothing Then Return -1
    Dim letters As New System.Text.StringBuilder
    For Each ch As Char In rAttr.Value
        If Char.IsLetter(ch) Then letters.Append(ch) Else Exit For
    Next
    If letters.Length = 0 Then Return -1
    Return ColLetterToNum(letters.ToString())
End Function

Function GetCellValue(c As System.Xml.XmlNode, _
        ss As System.Collections.Generic.List(Of String), _
        xm As System.Xml.XmlNamespaceManager) As String
    Dim tAttr  As System.Xml.XmlAttribute = c.Attributes("t")
    Dim isNode As System.Xml.XmlNode = c.SelectSingleNode("x:is/x:t", xm)
    Dim vNode  As System.Xml.XmlNode = c.SelectSingleNode("x:v", xm)
    If isNode IsNot Nothing Then Return isNode.InnerText
    If vNode IsNot Nothing Then
        If tAttr IsNot Nothing AndAlso tAttr.Value = "s" Then
            Dim idx As Integer = 0
            If Integer.TryParse(vNode.InnerText, idx) AndAlso idx >= 0 AndAlso idx < ss.Count Then
                Return ss(idx)
            End If
        Else
            Return vNode.InnerText
        End If
    End If
    Return ""
End Function

Function ColLetterToNum(col As String) As Integer
    Dim n As Integer = 0
    For Each ch As Char In col.ToUpper()
        n = n * 26 + (AscW(ch) - 64)
    Next
    Return n
End Function

Function ColLetter(n As Integer) As String
    Dim result As String = ""
    Do While n > 0
        Dim remainder As Integer = (n - 1) Mod 26
        result = Chr(65 + remainder) & result
        n = (n - 1) \ 26
    Loop
    Return result
End Function

Function SsAdd(v As String, ss As System.Collections.Generic.List(Of String), _
               ssIdx As System.Collections.Generic.Dictionary(Of String, Integer)) As Integer
    If ssIdx.ContainsKey(v) Then Return ssIdx(v)
    Dim i As Integer = ss.Count
    ss.Add(v) : ssIdx(v) = i
    Return i
End Function

Sub WriteXlsx(xlsxPath As String, asmName As String, _
        orgOps As System.Collections.Generic.List(Of String()), _
        partRows As System.Collections.Generic.List(Of Object()), _
        asmRows  As System.Collections.Generic.List(Of Object()), _
        Optional JobPackageMode As Boolean = False)

    Dim ss    As New System.Collections.Generic.List(Of String)
    Dim ssIdx As New System.Collections.Generic.Dictionary(Of String, Integer)( _
        System.StringComparer.Ordinal)

    SsAdd("Level", ss, ssIdx)          : SsAdd("Part Number", ss, ssIdx)
    SsAdd("Description", ss, ssIdx)    : SsAdd("Qty", ss, ssIdx)
    SsAdd("Type", ss, ssIdx)           : SsAdd("Material", ss, ssIdx)
    SsAdd("Thickness (mm)", ss, ssIdx) : SsAdd("Bends", ss, ssIdx)
    SsAdd("PPM_Holes", ss, ssIdx)      : SsAdd("PPM_Threads", ss, ssIdx)
    For Each op As String() In orgOps
        SsAdd(op(1) & " REQ?",  ss, ssIdx)
        SsAdd(op(1) & " DONE?", ss, ssIdx)
        SsAdd(op(1),             ss, ssIdx)
    Next
    SsAdd("✓",         ss, ssIdx)
    SsAdd("Item",      ss, ssIdx)
    SsAdd("QTY",       ss, ssIdx)
    SsAdd("Thickness", ss, ssIdx)
    For Each row As Object() In partRows
        SsAdd(CStr(row(1)), ss, ssIdx) : SsAdd(CStr(row(2)), ss, ssIdx)
        SsAdd(CStr(row(4)), ss, ssIdx) : SsAdd(CStr(row(5)), ss, ssIdx)
        If CStr(row(8)) <> "" Then SsAdd(CStr(row(8)), ss, ssIdx)
        If CStr(row(9)) <> "" Then SsAdd(CStr(row(9)), ss, ssIdx)
        If CStr(row(11)) <> "" Then SsAdd(CStr(row(11)), ss, ssIdx)
    Next
    For Each row As Object() In asmRows
        SsAdd(CStr(row(1)), ss, ssIdx) : SsAdd(CStr(row(2)), ss, ssIdx)
        SsAdd(CStr(row(4)), ss, ssIdx)
        If CStr(row(6)) <> "" Then SsAdd(CStr(row(6)), ss, ssIdx)
    Next

    Using archive As System.IO.Compression.ZipArchive = _
        System.IO.Compression.ZipFile.Open(xlsxPath, _
        System.IO.Compression.ZipArchiveMode.Create)

        ' JobPackageMode (D-681 step 2 / D-328): 3 sheets only, no
        ' REPORT -- BOM_FLAT takes REPORT's old slot (sheet3) so numbering
        ' stays clean/sequential (1,2,3) rather than leaving a gap.
        ' Non-JobPackageMode is BYTE-FOR-BYTE the original 4-sheet
        ' structure -- default behavior is completely unchanged.
        Dim sheetOverrides As String
        Dim sheetRels      As String
        Dim sheetsXml      As String

        If JobPackageMode Then
            sheetOverrides = _
                "<Override PartName=""/xl/worksheets/sheet1.xml"" ContentType=""application/vnd.openxmlformats-officedocument.spreadsheetml.worksheet+xml""/>" & _
                "<Override PartName=""/xl/worksheets/sheet2.xml"" ContentType=""application/vnd.openxmlformats-officedocument.spreadsheetml.worksheet+xml""/>" & _
                "<Override PartName=""/xl/worksheets/sheet3.xml"" ContentType=""application/vnd.openxmlformats-officedocument.spreadsheetml.worksheet+xml""/>"
            sheetRels = _
                "<Relationship Id=""rId1"" Type=""http://schemas.openxmlformats.org/officeDocument/2006/relationships/worksheet"" Target=""worksheets/sheet1.xml""/>" & _
                "<Relationship Id=""rId2"" Type=""http://schemas.openxmlformats.org/officeDocument/2006/relationships/worksheet"" Target=""worksheets/sheet2.xml""/>" & _
                "<Relationship Id=""rId3"" Type=""http://schemas.openxmlformats.org/officeDocument/2006/relationships/worksheet"" Target=""worksheets/sheet3.xml""/>" & _
                "<Relationship Id=""rId4"" Type=""http://schemas.openxmlformats.org/officeDocument/2006/relationships/sharedStrings"" Target=""sharedStrings.xml""/>" & _
                "<Relationship Id=""rId5"" Type=""http://schemas.openxmlformats.org/officeDocument/2006/relationships/styles"" Target=""styles.xml""/>"
            sheetsXml = _
                "<sheet name=""PARTS"" sheetId=""1"" r:id=""rId1""/>" & _
                "<sheet name=""ASSEMBLIES"" sheetId=""2"" r:id=""rId2""/>" & _
                "<sheet name=""BOM_FLAT"" sheetId=""3"" r:id=""rId3""/>"
        Else
            sheetOverrides = _
                "<Override PartName=""/xl/worksheets/sheet1.xml"" ContentType=""application/vnd.openxmlformats-officedocument.spreadsheetml.worksheet+xml""/>" & _
                "<Override PartName=""/xl/worksheets/sheet2.xml"" ContentType=""application/vnd.openxmlformats-officedocument.spreadsheetml.worksheet+xml""/>" & _
                "<Override PartName=""/xl/worksheets/sheet3.xml"" ContentType=""application/vnd.openxmlformats-officedocument.spreadsheetml.worksheet+xml""/>" & _
                "<Override PartName=""/xl/worksheets/sheet4.xml"" ContentType=""application/vnd.openxmlformats-officedocument.spreadsheetml.worksheet+xml""/>"
            sheetRels = _
                "<Relationship Id=""rId1"" Type=""http://schemas.openxmlformats.org/officeDocument/2006/relationships/worksheet"" Target=""worksheets/sheet1.xml""/>" & _
                "<Relationship Id=""rId2"" Type=""http://schemas.openxmlformats.org/officeDocument/2006/relationships/worksheet"" Target=""worksheets/sheet2.xml""/>" & _
                "<Relationship Id=""rId3"" Type=""http://schemas.openxmlformats.org/officeDocument/2006/relationships/worksheet"" Target=""worksheets/sheet3.xml""/>" & _
                "<Relationship Id=""rId4"" Type=""http://schemas.openxmlformats.org/officeDocument/2006/relationships/worksheet"" Target=""worksheets/sheet4.xml""/>" & _
                "<Relationship Id=""rId5"" Type=""http://schemas.openxmlformats.org/officeDocument/2006/relationships/sharedStrings"" Target=""sharedStrings.xml""/>" & _
                "<Relationship Id=""rId6"" Type=""http://schemas.openxmlformats.org/officeDocument/2006/relationships/styles"" Target=""styles.xml""/>"
            sheetsXml = _
                "<sheet name=""PARTS"" sheetId=""1"" r:id=""rId1""/>" & _
                "<sheet name=""ASSEMBLIES"" sheetId=""2"" r:id=""rId2""/>" & _
                "<sheet name=""REPORT"" sheetId=""3"" r:id=""rId3""/>" & _
                "<sheet name=""BOM_FLAT"" sheetId=""4"" r:id=""rId4""/>"
        End If

        WriteZipEntry(archive, "[Content_Types].xml", _
            "<?xml version=""1.0"" encoding=""UTF-8"" standalone=""yes""?>" & _
            "<Types xmlns=""http://schemas.openxmlformats.org/package/2006/content-types"">" & _
            "<Default Extension=""rels"" ContentType=""application/vnd.openxmlformats-package.relationships+xml""/>" & _
            "<Default Extension=""xml"" ContentType=""application/xml""/>" & _
            "<Override PartName=""/xl/workbook.xml"" ContentType=""application/vnd.openxmlformats-officedocument.spreadsheetml.sheet.main+xml""/>" & _
            sheetOverrides & _
            "<Override PartName=""/xl/sharedStrings.xml"" ContentType=""application/vnd.openxmlformats-officedocument.spreadsheetml.sharedStrings+xml""/>" & _
            "<Override PartName=""/xl/styles.xml"" ContentType=""application/vnd.openxmlformats-officedocument.spreadsheetml.styles+xml""/>" & _
            "</Types>")

        WriteZipEntry(archive, "_rels/.rels", _
            "<?xml version=""1.0"" encoding=""UTF-8"" standalone=""yes""?>" & _
            "<Relationships xmlns=""http://schemas.openxmlformats.org/package/2006/relationships"">" & _
            "<Relationship Id=""rId1"" Type=""http://schemas.openxmlformats.org/officeDocument/2006/relationships/officeDocument"" Target=""xl/workbook.xml""/>" & _
            "</Relationships>")

        WriteZipEntry(archive, "xl/_rels/workbook.xml.rels", _
            "<?xml version=""1.0"" encoding=""UTF-8"" standalone=""yes""?>" & _
            "<Relationships xmlns=""http://schemas.openxmlformats.org/package/2006/relationships"">" & _
            sheetRels & _
            "</Relationships>")

        WriteZipEntry(archive, "xl/workbook.xml", _
            "<?xml version=""1.0"" encoding=""UTF-8"" standalone=""yes""?>" & _
            "<workbook xmlns=""http://schemas.openxmlformats.org/spreadsheetml/2006/main"" " & _
            "xmlns:r=""http://schemas.openxmlformats.org/officeDocument/2006/relationships"">" & _
            "<sheets>" & _
            sheetsXml & _
            "</sheets></workbook>")

        WriteZipEntry(archive, "xl/styles.xml", BuildStylesXml())

        Dim sbSS As New System.Text.StringBuilder
        sbSS.Append("<?xml version=""1.0"" encoding=""UTF-8"" standalone=""yes""?>")
        sbSS.Append("<sst xmlns=""http://schemas.openxmlformats.org/spreadsheetml/2006/main"" count=""")
        sbSS.Append(ss.Count) : sbSS.Append(""" uniqueCount=""")
        sbSS.Append(ss.Count) : sbSS.Append(""">")
        For Each sv As String In ss
            sbSS.Append("<si><t xml:space=""preserve"">")
            sbSS.Append(XmlEsc(sv)) : sbSS.Append("</t></si>")
        Next
        sbSS.Append("</sst>")
        WriteZipEntry(archive, "xl/sharedStrings.xml", sbSS.ToString())

        WriteZipEntry(archive, "xl/worksheets/sheet1.xml", _
            BuildPartsSheet(orgOps, partRows, ssIdx))
        WriteZipEntry(archive, "xl/worksheets/sheet2.xml", _
            BuildAsmsSheet(orgOps, asmRows, ssIdx))
        If JobPackageMode Then
            ' sheet3 = BOM_FLAT (REPORT skipped entirely -- D-328)
            WriteZipEntry(archive, "xl/worksheets/sheet3.xml", _
                BuildBomFlatSheet(orgOps, partRows, ssIdx))
        Else
            WriteZipEntry(archive, "xl/worksheets/sheet3.xml", _
                BuildReportSheet(asmName, orgOps, partRows, asmRows))
            WriteZipEntry(archive, "xl/worksheets/sheet4.xml", _
                BuildBomFlatSheet(orgOps, partRows, ssIdx))
        End If
    End Using
End Sub

Sub WriteZipEntry(archive As System.IO.Compression.ZipArchive, _
        entryName As String, content As String)
    Dim entry As System.IO.Compression.ZipArchiveEntry = _
        archive.CreateEntry(entryName, System.IO.Compression.CompressionLevel.Optimal)
    Using s As System.IO.Stream = entry.Open()
        Dim b() As Byte = System.Text.Encoding.UTF8.GetBytes(content)
        s.Write(b, 0, b.Length)
    End Using
End Sub

Function XmlEsc(sv As String) As String
    Return sv.Replace("&", "&amp;").Replace("<", "&lt;"). _
              Replace(">", "&gt;").Replace("""", "&quot;")
End Function

Function BuildStylesXml() As String
    Return "<?xml version=""1.0"" encoding=""UTF-8"" standalone=""yes""?>" & _
        "<styleSheet xmlns=""http://schemas.openxmlformats.org/spreadsheetml/2006/main"">" & _
        "<fonts count=""2""><font><sz val=""10""/><name val=""Calibri""/></font>" & _
        "<font><b/><sz val=""10""/><name val=""Calibri""/></font></fonts>" & _
        "<fills count=""3""><fill><patternFill patternType=""none""/></fill>" & _
        "<fill><patternFill patternType=""gray125""/></fill>" & _
        "<fill><patternFill patternType=""solid""><fgColor rgb=""FFD29922""/></patternFill></fill></fills>" & _
        "<borders count=""1""><border><left/><right/><top/><bottom/><diagonal/></border></borders>" & _
        "<cellStyleXfs count=""1""><xf numFmtId=""0"" fontId=""0"" fillId=""0"" borderId=""0""/></cellStyleXfs>" & _
        "<cellXfs count=""3"">" & _
        "<xf numFmtId=""0"" fontId=""0"" fillId=""0"" borderId=""0"" xfId=""0""/>" & _
        "<xf numFmtId=""0"" fontId=""1"" fillId=""0"" borderId=""0"" xfId=""0""/>" & _
        "<xf numFmtId=""0"" fontId=""0"" fillId=""2"" borderId=""0"" xfId=""0""/>" & _
        "</cellXfs></styleSheet>"
End Function

Function BuildPartsSheet(orgOps As System.Collections.Generic.List(Of String()), _
        rows As System.Collections.Generic.List(Of Object()), _
        ssIdx As System.Collections.Generic.Dictionary(Of String, Integer)) As String

    Dim sb As New System.Text.StringBuilder
    sb.Append("<?xml version=""1.0"" encoding=""UTF-8"" standalone=""yes""?>")
    sb.Append("<worksheet xmlns=""http://schemas.openxmlformats.org/spreadsheetml/2006/main"">")
    sb.Append("<sheetViews><sheetView workbookViewId=""0"">")
    sb.Append("<pane state=""frozen"" ySplit=""1"" topLeftCell=""A2"" activePane=""bottomLeft""/>")
    sb.Append("</sheetView></sheetViews><sheetData>")

    Dim fixedH() As String = {"Item","Level","Part Number","Description","Qty","Type", _
        "Material","Thickness (mm)","Bends","PPM_Holes","PPM_Threads"}
    Dim col As Integer = 1
    sb.Append("<row r=""1"">")
    For Each h As String In fixedH
        sb.Append("<c r=""" & ColLetter(col) & "1"" t=""s"" s=""1""><v>")
        sb.Append(ssIdx(h)) : sb.Append("</v></c>") : col += 1
    Next
    For Each op As String() In orgOps
        sb.Append("<c r=""" & ColLetter(col) & "1"" t=""s"" s=""1""><v>")
        sb.Append(ssIdx(op(1) & " REQ?")) : sb.Append("</v></c>") : col += 1
        sb.Append("<c r=""" & ColLetter(col) & "1"" t=""s"" s=""1""><v>")
        sb.Append(ssIdx(op(1) & " DONE?")) : sb.Append("</v></c>") : col += 1
    Next
    sb.Append("</row>")

    Dim rn As Integer = 2
    For Each row As Object() In rows
        col = 1
        sb.Append("<row r=""" & rn & """>")
        SCell(sb, col, rn, CStr(row(11)), ssIdx) : col += 1
        NCell(sb, col, rn, CInt(row(0))) : col += 1
        SCell(sb, col, rn, CStr(row(1)), ssIdx) : col += 1
        SCell(sb, col, rn, CStr(row(2)), ssIdx) : col += 1
        NCell(sb, col, rn, CInt(row(3))) : col += 1
        SCell(sb, col, rn, CStr(row(4)), ssIdx) : col += 1
        SCell(sb, col, rn, CStr(row(5)), ssIdx) : col += 1
        Dim thk As Double = CDbl(row(6))
        If thk > 0 Then
            DCell(sb, col, rn, thk)
        Else
            sb.Append("<c r=""" & ColLetter(col) & rn & """/>")
        End If
        col += 1
        NCell(sb, col, rn, CInt(row(7))) : col += 1
        SCell(sb, col, rn, CStr(row(8)), ssIdx) : col += 1
        SCell(sb, col, rn, CStr(row(9)), ssIdx) : col += 1
        Dim opf As System.Collections.Generic.Dictionary(Of String, Integer) = _
            CType(row(10), System.Collections.Generic.Dictionary(Of String, Integer))
        For Each op As String() In orgOps
            Dim v As Integer = 0
            If opf.ContainsKey(op(0)) Then v = opf(op(0))
            If v = 1 Then SCell(sb, col, rn, "✓", ssIdx) _
            Else sb.Append("<c r=""" & ColLetter(col) & rn & """/>")
            col += 1
            sb.Append("<c r=""" & ColLetter(col) & rn & """/>") : col += 1
        Next
        sb.Append("</row>")
        rn += 1
    Next
    sb.Append("</sheetData></worksheet>")
    Return sb.ToString()
End Function

Function BuildAsmsSheet(orgOps As System.Collections.Generic.List(Of String()), _
        rows As System.Collections.Generic.List(Of Object()), _
        ssIdx As System.Collections.Generic.Dictionary(Of String, Integer)) As String

    Dim sb As New System.Text.StringBuilder
    sb.Append("<?xml version=""1.0"" encoding=""UTF-8"" standalone=""yes""?>")
    sb.Append("<worksheet xmlns=""http://schemas.openxmlformats.org/spreadsheetml/2006/main"">")
    sb.Append("<sheetViews><sheetView workbookViewId=""0"">")
    sb.Append("<pane state=""frozen"" ySplit=""1"" topLeftCell=""A2"" activePane=""bottomLeft""/>")
    sb.Append("</sheetView></sheetViews><sheetData>")

    Dim fixedH() As String = {"Item","Level","Part Number","Description","Qty","Type"}
    Dim col As Integer = 1
    sb.Append("<row r=""1"">")
    For Each h As String In fixedH
        sb.Append("<c r=""" & ColLetter(col) & "1"" t=""s"" s=""1""><v>")
        sb.Append(ssIdx(h)) : sb.Append("</v></c>") : col += 1
    Next
    For Each op As String() In orgOps
        sb.Append("<c r=""" & ColLetter(col) & "1"" t=""s"" s=""1""><v>")
        sb.Append(ssIdx(op(1) & " REQ?")) : sb.Append("</v></c>") : col += 1
        sb.Append("<c r=""" & ColLetter(col) & "1"" t=""s"" s=""1""><v>")
        sb.Append(ssIdx(op(1) & " DONE?")) : sb.Append("</v></c>") : col += 1
    Next
    sb.Append("</row>")

    Dim rn As Integer = 2
    For Each row As Object() In rows
        col = 1
        Dim dtype  As String  = CStr(row(4))
        Dim isWeld As Boolean = (dtype = "Weld Assy")
        Dim rAttr  As String  = If(isWeld, " s=""2"" customFormat=""1""", "")
        Dim cs     As Integer = If(isWeld, 2, 0)
        sb.Append("<row r=""" & rn & """" & rAttr & ">")
        SCellS(sb, col, rn, CStr(row(6)), ssIdx, cs) : col += 1
        NCellS(sb, col, rn, CInt(row(0)), cs) : col += 1
        SCellS(sb, col, rn, CStr(row(1)), ssIdx, cs) : col += 1
        SCellS(sb, col, rn, CStr(row(2)), ssIdx, cs) : col += 1
        NCellS(sb, col, rn, CInt(row(3)), cs) : col += 1
        SCellS(sb, col, rn, dtype, ssIdx, cs) : col += 1
        Dim opf As System.Collections.Generic.Dictionary(Of String, Integer) = _
            CType(row(5), System.Collections.Generic.Dictionary(Of String, Integer))
        For Each op As String() In orgOps
            Dim v As Integer = 0
            If opf.ContainsKey(op(0)) Then v = opf(op(0))
            If v = 1 Then SCellS(sb, col, rn, "✓", ssIdx, cs) _
            Else sb.Append("<c r=""" & ColLetter(col) & rn & """" & _
                If(cs > 0, " s=""" & cs & """", "") & "/>")
            col += 1
            sb.Append("<c r=""" & ColLetter(col) & rn & """" & _
                If(cs > 0, " s=""" & cs & """", "") & "/>") : col += 1
        Next
        sb.Append("</row>")
        rn += 1
    Next
    sb.Append("</sheetData></worksheet>")
    Return sb.ToString()
End Function

Sub SCell(sb As System.Text.StringBuilder, col As Integer, rn As Integer, _
        val As String, ssIdx As System.Collections.Generic.Dictionary(Of String, Integer))
    If val = "" OrElse Not ssIdx.ContainsKey(val) Then
        sb.Append("<c r=""" & ColLetter(col) & rn & """/>")
    Else
        sb.Append("<c r=""" & ColLetter(col) & rn & """ t=""s""><v>")
        sb.Append(ssIdx(val)) : sb.Append("</v></c>")
    End If
End Sub

Sub NCell(sb As System.Text.StringBuilder, col As Integer, rn As Integer, val As Integer)
    sb.Append("<c r=""" & ColLetter(col) & rn & """><v>")
    sb.Append(val) : sb.Append("</v></c>")
End Sub

Sub DCell(sb As System.Text.StringBuilder, col As Integer, rn As Integer, val As Double)
    sb.Append("<c r=""" & ColLetter(col) & rn & """><v>")
    sb.Append(val.ToString("0.##", System.Globalization.CultureInfo.InvariantCulture))
    sb.Append("</v></c>")
End Sub

Sub SCellS(sb As System.Text.StringBuilder, col As Integer, rn As Integer, _
        val As String, ssIdx As System.Collections.Generic.Dictionary(Of String, Integer), _
        style As Integer)
    Dim sa As String = If(style > 0, " s=""" & style & """", "")
    If val = "" OrElse Not ssIdx.ContainsKey(val) Then
        sb.Append("<c r=""" & ColLetter(col) & rn & """" & sa & "/>")
    Else
        sb.Append("<c r=""" & ColLetter(col) & rn & """" & sa & " t=""s""><v>")
        sb.Append(ssIdx(val)) : sb.Append("</v></c>")
    End If
End Sub

Sub NCellS(sb As System.Text.StringBuilder, col As Integer, rn As Integer, _
        val As Integer, style As Integer)
    Dim sa As String = If(style > 0, " s=""" & style & """", "")
    sb.Append("<c r=""" & ColLetter(col) & rn & """" & sa & "><v>")
    sb.Append(val) : sb.Append("</v></c>")
End Sub

Function EmptySheet() As String
    Return "<?xml version=""1.0"" encoding=""UTF-8"" standalone=""yes""?>" & _
        "<worksheet xmlns=""http://schemas.openxmlformats.org/spreadsheetml/2006/main"">" & _
        "<sheetData/></worksheet>"
End Function

' ════════════════════════════════════════════════════════════════
' Inline-string cell helpers (REPORT sheet uses t="inlineStr")
' ════════════════════════════════════════════════════════════════

Sub RICell(sb As System.Text.StringBuilder, col As Integer, rn As Integer, _
        val As String, bold As Integer)
    Dim sa As String = If(bold = 1, " s=""1""", "")
    sb.Append("<c r=""" & ColLetter(col) & rn & """" & sa & " t=""inlineStr""><is><t>")
    sb.Append(XmlEsc(val)) : sb.Append("</t></is></c>")
End Sub

Sub RICellS(sb As System.Text.StringBuilder, col As Integer, rn As Integer, _
        val As String, style As Integer)
    sb.Append("<c r=""" & ColLetter(col) & rn & """ s=""" & style & """ t=""inlineStr""><is><t>")
    sb.Append(XmlEsc(val)) : sb.Append("</t></is></c>")
End Sub

Sub RIRow2(sb As System.Text.StringBuilder, rn As Integer, label As String, num As Integer)
    sb.Append("<row r=""" & rn & """>")
    RICell(sb, 1, rn, label, 0)
    sb.Append("<c r=""B" & rn & """><v>") : sb.Append(num) : sb.Append("</v></c>")
    sb.Append("</row>")
End Sub

' ════════════════════════════════════════════════════════════════
' REPORT sheet (sheet3)
' ════════════════════════════════════════════════════════════════

Function BuildReportSheet(asmName As String, _
        orgOps As System.Collections.Generic.List(Of String()), _
        partRows As System.Collections.Generic.List(Of Object()), _
        asmRows  As System.Collections.Generic.List(Of Object())) As String

    Dim sb As New System.Text.StringBuilder
    Dim rn As Integer = 1
    Dim ts As String = DateTime.Now.ToString("yyyy-MM-dd HH:mm", _
        System.Globalization.CultureInfo.InvariantCulture)

    sb.Append("<?xml version=""1.0"" encoding=""UTF-8"" standalone=""yes""?>")
    sb.Append("<worksheet xmlns=""http://schemas.openxmlformats.org/spreadsheetml/2006/main"">")
    sb.Append("<sheetData>")

    ' Title + timestamp
    sb.Append("<row r=""" & rn & """>")
    RICell(sb, 1, rn, asmName & "  —  REPORT", 1)
    sb.Append("</row>") : rn += 1

    sb.Append("<row r=""" & rn & """>")
    RICell(sb, 1, rn, "Exportovano / Exported: " & ts, 0)
    sb.Append("</row>") : rn += 1

    sb.Append("<row r=""" & rn & """/>") : rn += 1

    ' Counts
    RIRow2(sb, rn, "Ukupno delova / Total unique parts:", partRows.Count) : rn += 1
    RIRow2(sb, rn, "Ukupno sklopova / Total assemblies:", asmRows.Count) : rn += 1

    sb.Append("<row r=""" & rn & """/>") : rn += 1

    ' OPERATION COMPLETION table
    ' REQ = parts in BOM with this op flagged 1. DONE = 0 until manual post-export fill.
    sb.Append("<row r=""" & rn & """>")
    RICell(sb, 1, rn, "OPERACIJE / OPERATION COMPLETION", 1)
    sb.Append("</row>") : rn += 1

    sb.Append("<row r=""" & rn & """>")
    RICell(sb, 1, rn, "Op.ID", 1)
    RICell(sb, 2, rn, "Operacija / Operation", 1)
    RICell(sb, 3, rn, "Kategorija / Category", 1)
    RICell(sb, 4, rn, "REQ " & ChrW(10003), 1)
    RICell(sb, 5, rn, "DONE " & ChrW(10003), 1)
    RICell(sb, 6, rn, "% Komplet / Completion %", 1)
    RICell(sb, 7, rn, "Status", 1)
    RICell(sb, 8, rn, "Notes", 1)
    sb.Append("</row>") : rn += 1

    For Each op As String() In orgOps
        Dim req     As Integer = 0
        Dim doneVal As Integer = 0  ' placeholder — replace with real DONE lookup when wired
        For Each row As Object() In partRows
            Dim opf As System.Collections.Generic.Dictionary(Of String, Integer) = _
                CType(row(10), System.Collections.Generic.Dictionary(Of String, Integer))
            If opf.ContainsKey(op(0)) AndAlso opf(op(0)) = 1 Then req += 1
        Next
        Dim pct As String = If(req > 0, _
            (doneVal * 100.0 / req).ToString("0.0", _
            System.Globalization.CultureInfo.InvariantCulture) & "%", "N/A")
        sb.Append("<row r=""" & rn & """>")
        RICell(sb, 1, rn, op(0), 0)
        RICell(sb, 2, rn, op(1), 0)
        RICell(sb, 3, rn, op(2), 0)
        sb.Append("<c r=""D" & rn & """><v>") : sb.Append(req) : sb.Append("</v></c>")
        sb.Append("<c r=""E" & rn & """><v>") : sb.Append(doneVal) : sb.Append("</v></c>")
        RICell(sb, 6, rn, pct, 0)
        RICell(sb, 7, rn, "—", 0)
        sb.Append("</row>") : rn += 1
    Next

    sb.Append("<row r=""" & rn & """/>") : rn += 1

    ' Weld assemblies list
    Dim weldRows As New System.Collections.Generic.List(Of Object())
    For Each row As Object() In asmRows
        If CStr(row(4)) = "Weld Assy" Then weldRows.Add(row)
    Next

    sb.Append("<row r=""" & rn & """>")
    RICell(sb, 1, rn, "Zavarivački sklopovi / Weld Assemblies: " & weldRows.Count, 1)
    sb.Append("</row>") : rn += 1

    If weldRows.Count > 0 Then
        sb.Append("<row r=""" & rn & """>")
        RICell(sb, 1, rn, "Part Number", 1) : RICell(sb, 2, rn, "Description", 1)
        Dim hc As Integer = 3
        For Each op As String() In orgOps
            RICell(sb, hc, rn, op(1), 1) : hc += 1
        Next
        sb.Append("</row>") : rn += 1

        For Each row As Object() In weldRows
            sb.Append("<row r=""" & rn & """>")
            RICell(sb, 1, rn, CStr(row(1)), 0)
            RICell(sb, 2, rn, CStr(row(2)), 0)
            Dim dc As Integer = 3
            Dim opf As System.Collections.Generic.Dictionary(Of String, Integer) = _
                CType(row(5), System.Collections.Generic.Dictionary(Of String, Integer))
            For Each op As String() In orgOps
                Dim v As Integer = 0
                If opf.ContainsKey(op(0)) Then v = opf(op(0))
                RICell(sb, dc, rn, If(v = 1, "1", "0"), 0) : dc += 1
            Next
            sb.Append("</row>") : rn += 1
        Next
    End If

    sb.Append("<row r=""" & rn & """/>") : rn += 1

    ' Zero-ops items — amber fill (style 2)
    Dim zeroRows As New System.Collections.Generic.List(Of String())
    For Each row As Object() In partRows
        Dim opf As System.Collections.Generic.Dictionary(Of String, Integer) = _
            CType(row(10), System.Collections.Generic.Dictionary(Of String, Integer))
        Dim hasOp As Boolean = False
        For Each op As String() In orgOps
            If opf.ContainsKey(op(0)) AndAlso opf(op(0)) = 1 Then hasOp = True : Exit For
        Next
        If Not hasOp Then zeroRows.Add(New String() {CStr(row(1)), CStr(row(2)), "Part"})
    Next
    For Each row As Object() In asmRows
        Dim opf As System.Collections.Generic.Dictionary(Of String, Integer) = _
            CType(row(5), System.Collections.Generic.Dictionary(Of String, Integer))
        Dim hasOp As Boolean = False
        For Each op As String() In orgOps
            If opf.ContainsKey(op(0)) AndAlso opf(op(0)) = 1 Then hasOp = True : Exit For
        Next
        If Not hasOp Then zeroRows.Add(New String() {CStr(row(1)), CStr(row(2)), CStr(row(4))})
    Next

    sb.Append("<row r=""" & rn & """>")
    RICell(sb, 1, rn, "Bez operacija / Zero ops: " & zeroRows.Count, 1)
    sb.Append("</row>") : rn += 1

    If zeroRows.Count > 0 Then
        sb.Append("<row r=""" & rn & """>")
        RICell(sb, 1, rn, "Part Number", 1)
        RICell(sb, 2, rn, "Description", 1)
        RICell(sb, 3, rn, "Type", 1)
        sb.Append("</row>") : rn += 1
        For Each row As String() In zeroRows
            sb.Append("<row r=""" & rn & """>")
            RICellS(sb, 1, rn, row(0), 2)
            RICellS(sb, 2, rn, row(1), 2)
            RICellS(sb, 3, rn, row(2), 2)
            sb.Append("</row>") : rn += 1
        Next
    End If

    sb.Append("</sheetData></worksheet>")
    Return sb.ToString()
End Function

' ════════════════════════════════════════════════════════════════
' BOM_FLAT sheet (sheet4)
' ════════════════════════════════════════════════════════════════

Function BuildBomFlatSheet(orgOps As System.Collections.Generic.List(Of String()), _
        partRows As System.Collections.Generic.List(Of Object()), _
        ssIdx As System.Collections.Generic.Dictionary(Of String, Integer)) As String

    Dim sb As New System.Text.StringBuilder
    sb.Append("<?xml version=""1.0"" encoding=""UTF-8"" standalone=""yes""?>")
    sb.Append("<worksheet xmlns=""http://schemas.openxmlformats.org/spreadsheetml/2006/main"">")
    sb.Append("<sheetViews><sheetView workbookViewId=""0"">")
    sb.Append("<pane state=""frozen"" ySplit=""1"" topLeftCell=""A2"" activePane=""bottomLeft""/>")
    sb.Append("</sheetView></sheetViews><sheetData>")

    ' Fixed headers — case matches ImportBOM VBA case-insensitive lookup (D-247)
    Dim fixedH() As String = {"Item","Part Number","Description","QTY", _
        "Material","Thickness","Bends","PPM_Holes","PPM_Threads"}
    Dim col As Integer = 1
    sb.Append("<row r=""1"">")
    For Each h As String In fixedH
        sb.Append("<c r=""" & ColLetter(col) & "1"" t=""s"" s=""1""><v>")
        sb.Append(ssIdx(h)) : sb.Append("</v></c>") : col += 1
    Next
    For Each op As String() In orgOps
        sb.Append("<c r=""" & ColLetter(col) & "1"" t=""s"" s=""1""><v>")
        sb.Append(ssIdx(op(1))) : sb.Append("</v></c>") : col += 1
    Next
    sb.Append("</row>")

    ' Deduplicate by PN: first occurrence wins for all fields except Qty (sum) and
    ' op flags (max — 1 if any occurrence has 1). New opFlags dict to avoid mutating partRows.
    Dim flatMap As New System.Collections.Generic.Dictionary(Of String, Object())( _
        System.StringComparer.OrdinalIgnoreCase)
    Dim flatOrder As New System.Collections.Generic.List(Of String)
    For Each row As Object() In partRows
        Dim fpn As String = CStr(row(1))
        If Not flatMap.ContainsKey(fpn) Then
            Dim srcOpf As System.Collections.Generic.Dictionary(Of String, Integer) = _
                CType(row(10), System.Collections.Generic.Dictionary(Of String, Integer))
            Dim newOpf As New System.Collections.Generic.Dictionary(Of String, Integer)( _
                System.StringComparer.OrdinalIgnoreCase)
            For Each op As String() In orgOps
                Dim v As Integer = 0
                If srcOpf.ContainsKey(op(0)) Then v = srcOpf(op(0))
                newOpf(op(0)) = v
            Next
            flatMap(fpn) = New Object() {row(0), row(1), row(2), row(3), row(4), _
                row(5), row(6), row(7), row(8), row(9), newOpf, row(11)}
            flatOrder.Add(fpn)
        Else
            Dim fx As Object() = flatMap(fpn)
            fx(3) = CInt(fx(3)) + CInt(row(3))
            Dim fxOpf As System.Collections.Generic.Dictionary(Of String, Integer) = _
                CType(fx(10), System.Collections.Generic.Dictionary(Of String, Integer))
            Dim rOpf As System.Collections.Generic.Dictionary(Of String, Integer) = _
                CType(row(10), System.Collections.Generic.Dictionary(Of String, Integer))
            For Each op As String() In orgOps
                If rOpf.ContainsKey(op(0)) AndAlso rOpf(op(0)) > 0 Then fxOpf(op(0)) = 1
            Next
        End If
    Next

    Dim rn   As Integer = 2
    Dim item As Integer = 1
    For Each fpn As String In flatOrder
        Dim row As Object() = flatMap(fpn)
        col = 1
        sb.Append("<row r=""" & rn & """>")
        NCell(sb, col, rn, item) : col += 1
        SCell(sb, col, rn, CStr(row(1)), ssIdx) : col += 1
        SCell(sb, col, rn, CStr(row(2)), ssIdx) : col += 1
        NCell(sb, col, rn, CInt(row(3))) : col += 1
        SCell(sb, col, rn, CStr(row(5)), ssIdx) : col += 1
        Dim thk As Double = CDbl(row(6))
        If thk > 0 Then DCell(sb, col, rn, thk) _
        Else sb.Append("<c r=""" & ColLetter(col) & rn & """/>")
        col += 1
        NCell(sb, col, rn, CInt(row(7))) : col += 1
        SCell(sb, col, rn, CStr(row(8)), ssIdx) : col += 1
        SCell(sb, col, rn, CStr(row(9)), ssIdx) : col += 1
        Dim opf As System.Collections.Generic.Dictionary(Of String, Integer) = _
            CType(row(10), System.Collections.Generic.Dictionary(Of String, Integer))
        For Each op As String() In orgOps
            Dim v As Integer = 0
            If opf.ContainsKey(op(0)) Then v = opf(op(0))
            If v = 1 Then SCell(sb, col, rn, "✓", ssIdx) _
            Else sb.Append("<c r=""" & ColLetter(col) & rn & """/>")
            col += 1
        Next
        sb.Append("</row>")
        rn += 1 : item += 1
    Next

    sb.Append("</sheetData></worksheet>")
    Return sb.ToString()
End Function

' ════════════════════════════════════════════════════════════════
' Summary dialog — auto-closes after 3000 ms
' ════════════════════════════════════════════════════════════════

Sub ShowSummaryDialog(nParts As Integer, nAsms As Integer, xlsxPath As String, _
        Optional purchasedNames As System.Collections.Generic.List(Of String) = Nothing)
    Dim cBg      As System.Drawing.Color = System.Drawing.Color.FromArgb(59, 68, 83)
    Dim cSurface As System.Drawing.Color = System.Drawing.Color.FromArgb(72, 82, 98)
    Dim cAccent  As System.Drawing.Color = System.Drawing.Color.FromArgb(46, 125, 209)
    Dim cText    As System.Drawing.Color = System.Drawing.Color.FromArgb(230, 237, 243)
    Dim cGreen   As System.Drawing.Color = System.Drawing.Color.FromArgb(63, 185, 80)
    Dim fUI   As New System.Drawing.Font("Segoe UI", 9)
    Dim fBold As New System.Drawing.Font("Segoe UI", 9, System.Drawing.FontStyle.Bold)

    Dim hasPurchased As Boolean = (purchasedNames IsNot Nothing AndAlso purchasedNames.Count > 0)
    Dim extraH As Integer = If(hasPurchased, 20 + (purchasedNames.Count * 16), 0)

    Dim dlg As New System.Windows.Forms.Form
    dlg.Text            = "PPM - BOM Export"
    dlg.Size            = New System.Drawing.Size(520, 200 + extraH)
    dlg.StartPosition   = System.Windows.Forms.FormStartPosition.CenterScreen
    dlg.FormBorderStyle = System.Windows.Forms.FormBorderStyle.FixedDialog
    dlg.MaximizeBox     = False : dlg.MinimizeBox = False
    dlg.BackColor       = cBg
    dlg.AutoScaleMode   = System.Windows.Forms.AutoScaleMode.None

    Dim lblTitle As New System.Windows.Forms.Label
    lblTitle.Text      = "PPM BOM EXPORT"
    lblTitle.Font      = New System.Drawing.Font("Segoe UI", 10, System.Drawing.FontStyle.Bold)
    lblTitle.ForeColor = cAccent
    lblTitle.Location  = New System.Drawing.Point(20, 18)
    lblTitle.Size      = New System.Drawing.Size(480, 22)
    dlg.Controls.Add(lblTitle)

    Dim fname As String = System.IO.Path.GetFileName(xlsxPath)
    Dim lblMsg As New System.Windows.Forms.Label
    lblMsg.Text      = "Exportovano / Exported: " & nParts & " delova / parts,  " & _
                       nAsms & " sklopova / assemblies" & vbCrLf & fname
    lblMsg.Font      = fUI
    lblMsg.ForeColor = cGreen
    lblMsg.Location  = New System.Drawing.Point(20, 48)
    lblMsg.Size      = New System.Drawing.Size(480, 40)
    dlg.Controls.Add(lblMsg)

    ' NEW (OQ-205 / D-703 diagnostic): show which PurchasedUnit assemblies
    ' were detected -- added after a test where BOM output looked
    ' identical with/without marking, and there was no visibility into
    ' whether detection ran at all vs. ran and correctly found zero.
    If hasPurchased Then
        Dim lblPurch As New System.Windows.Forms.Label
        lblPurch.Text      = "PurchasedUnit detektovano (deca isključena) / detected (children excluded):" & _
            vbCrLf & String.Join(vbCrLf, purchasedNames)
        lblPurch.Font      = fUI
        lblPurch.ForeColor = System.Drawing.Color.FromArgb(210, 153, 34)
        lblPurch.Location  = New System.Drawing.Point(20, 90)
        lblPurch.Size      = New System.Drawing.Size(480, extraH)
        dlg.Controls.Add(lblPurch)
    End If

    Dim sep As New System.Windows.Forms.Label
    sep.BackColor = cSurface
    sep.Location  = New System.Drawing.Point(20, 96 + extraH)
    sep.Size      = New System.Drawing.Size(480, 1)
    dlg.Controls.Add(sep)

    Dim btnOK As New System.Windows.Forms.Button
    btnOK.Text      = "OK"
    btnOK.Font      = fBold
    btnOK.BackColor = cAccent : btnOK.ForeColor = cText
    btnOK.FlatStyle = System.Windows.Forms.FlatStyle.Flat
    btnOK.FlatAppearance.BorderColor = cAccent
    btnOK.Location     = New System.Drawing.Point(200, 114 + extraH)
    btnOK.Size         = New System.Drawing.Size(120, 34)
    btnOK.DialogResult = System.Windows.Forms.DialogResult.OK
    dlg.Controls.Add(btnOK)
    dlg.AcceptButton = btnOK

    Dim tmr As New System.Windows.Forms.Timer
    tmr.Interval = If(hasPurchased, 6000, 3000)
    AddHandler tmr.Tick, Sub(s, e)
        tmr.Stop()
        dlg.Close()
    End Sub
    tmr.Start()

    dlg.ShowDialog()
    tmr.Stop() : tmr.Dispose()
    fUI.Dispose() : fBold.Dispose()
End Sub
