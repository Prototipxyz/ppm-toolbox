' PPM_OperationsSetup.iLogicVb
' One-time operations setup rule for PPM toolbox.
' Reads ppm_global_operations.json, shows categorized checklist,
' writes ppm_operations_config.json with the org's selected operations.

AddReference "System.Drawing"
AddReference "System.Windows.Forms"

Sub Main()

    ' ── Auto-update check ────────────────────────────────────────
    Dim localPath   As String = "C:\PPM Cuts and Bends\iLogic\PPM_OperationsSetup.iLogicVb"
    Dim networkPath As String = "X:\USER\Gavrilović\iLogic\PPM_OperationsSetup.iLogicVb"
    Try
        If System.IO.File.Exists(networkPath) AndAlso System.IO.File.Exists(localPath) Then
            Dim netTime   As DateTime = System.IO.File.GetLastWriteTime(networkPath)
            Dim localTime As DateTime = System.IO.File.GetLastWriteTime(localPath)
            If netTime > localTime Then
                System.IO.File.Copy(networkPath, localPath, True)
                System.Windows.Forms.MessageBox.Show( _
                    "Nova verzija je instalirana." & vbCrLf & _
                    "New version installed." & vbCrLf & vbCrLf & _
                    "Pokrenite makro ponovo." & vbCrLf & _
                    "Please run the macro again.", _
                    "PPM - Azuriranje / Update", _
                    System.Windows.Forms.MessageBoxButtons.OK, _
                    System.Windows.Forms.MessageBoxIcon.Information)
                Exit Sub
            End If
        End If
    Catch : End Try
    ' ─────────────────────────────────────────────────────────────

    ' ── Palette (D-258) ──────────────────────────────────────────
    Dim cBg      As System.Drawing.Color = System.Drawing.Color.FromArgb(59, 68, 83)
    Dim cSurface As System.Drawing.Color = System.Drawing.Color.FromArgb(72, 82, 98)
    Dim cAccent  As System.Drawing.Color = System.Drawing.Color.FromArgb(46, 125, 209)
    Dim cText    As System.Drawing.Color = System.Drawing.Color.FromArgb(230, 237, 243)
    Dim cSub     As System.Drawing.Color = System.Drawing.Color.FromArgb(180, 190, 200)
    Dim cGreen   As System.Drawing.Color = System.Drawing.Color.FromArgb(63, 185, 80)
    Dim cAmber   As System.Drawing.Color = System.Drawing.Color.FromArgb(210, 153, 34)

    Dim fUI   As New System.Drawing.Font("Segoe UI", 9)
    Dim fSub  As New System.Drawing.Font("Segoe UI", 8)
    Dim fBold As New System.Drawing.Font("Segoe UI", 9, System.Drawing.FontStyle.Bold)

    ' ── Paths ────────────────────────────────────────────────────
    Const CONFIG_DIR      As String = "X:\USER\Gavrilović\iLogic\config"
    Const GLOBAL_OPS_PATH As String = "X:\USER\Gavrilović\iLogic\config\ppm_global_operations.json"
    Const ORG_CONFIG_PATH As String = "X:\USER\Gavrilović\iLogic\config\ppm_operations_config.json"

    ' ── Ensure config directory exists ───────────────────────────
    Try
        If Not System.IO.Directory.Exists(CONFIG_DIR) Then
            System.IO.Directory.CreateDirectory(CONFIG_DIR)
        End If
    Catch ex As Exception
        ShowError("Ne mogu da kreiram config folder:" & vbCrLf & _
                  "Cannot create config folder:" & vbCrLf & vbCrLf & ex.Message)
        GoTo Cleanup
    End Try

    ' ── Load global operations JSON ───────────────────────────────
    ' Each entry parsed into String() {id, name, category, description}
    If Not System.IO.File.Exists(GLOBAL_OPS_PATH) Then
        ShowError("Nije pronađen globalni JSON:" & vbCrLf & _
                  "Global operations JSON not found:" & vbCrLf & vbCrLf & GLOBAL_OPS_PATH)
        GoTo Cleanup
    End If

    Dim allOps As New System.Collections.Generic.List(Of String())
    Try
        Dim raw As String = System.IO.File.ReadAllText(GLOBAL_OPS_PATH, System.Text.Encoding.UTF8)
        ParseGlobalOps(raw, allOps)
    Catch ex As Exception
        ShowError("Greška pri čitanju globalnog JSON-a:" & vbCrLf & _
                  "Error reading global operations JSON:" & vbCrLf & vbCrLf & ex.Message)
        GoTo Cleanup
    End Try

    If allOps.Count = 0 Then
        ShowError("Globalni JSON je prazan ili nije ispravno formatiran." & vbCrLf & _
                  "Global operations JSON is empty or malformed.")
        GoTo Cleanup
    End If

    ' Sort alphabetically by category, then by id within category,
    ' so all entries for a category are contiguous in the dialog.
    allOps.Sort(Function(a, b)
        Dim c As Integer = String.Compare(a(2), b(2), StringComparison.OrdinalIgnoreCase)
        If c <> 0 Then Return c
        Return String.Compare(a(0), b(0), StringComparison.OrdinalIgnoreCase)
    End Function)

    ' ── Load existing org config for pre-selection ────────────────
    Dim preSelectedIds As New System.Collections.Generic.HashSet(Of String)( _
        System.StringComparer.OrdinalIgnoreCase)
    Dim configLoaded As Boolean = False
    If System.IO.File.Exists(ORG_CONFIG_PATH) Then
        Try
            Dim cfgRaw As String = System.IO.File.ReadAllText(ORG_CONFIG_PATH, System.Text.Encoding.UTF8)
            ParseOrgConfigIds(cfgRaw, preSelectedIds)
            configLoaded = (preSelectedIds.Count > 0)
        Catch : End Try
    End If

    ' ── Setup dialog ──────────────────────────────────────────────
    Dim dlg As New System.Windows.Forms.Form
    dlg.Text            = "PPM - Postavljanje operacija / Operations Setup"
    dlg.Size            = New System.Drawing.Size(620, 690)
    dlg.StartPosition   = System.Windows.Forms.FormStartPosition.CenterScreen
    dlg.FormBorderStyle = System.Windows.Forms.FormBorderStyle.FixedDialog
    dlg.BackColor       = cBg
    dlg.MaximizeBox     = False : dlg.MinimizeBox = False
    dlg.AutoScaleMode   = System.Windows.Forms.AutoScaleMode.None

    ' Title
    Dim lblTitle As New System.Windows.Forms.Label
    lblTitle.Text      = "PPM OPERATIONS SETUP"
    lblTitle.Font      = New System.Drawing.Font("Segoe UI", 10, System.Drawing.FontStyle.Bold)
    lblTitle.ForeColor = cAccent
    lblTitle.Location  = New System.Drawing.Point(20, 18)
    lblTitle.Size      = New System.Drawing.Size(576, 20)
    dlg.Controls.Add(lblTitle)

    ' Subtitle
    Dim lblSubtitle As New System.Windows.Forms.Label
    lblSubtitle.Text      = "Izaberite operacije koje vaša kompanija koristi / Select operations used by your company"
    lblSubtitle.Font      = fSub
    lblSubtitle.ForeColor = cSub
    lblSubtitle.Location  = New System.Drawing.Point(20, 42)
    lblSubtitle.Size      = New System.Drawing.Size(576, 16)
    dlg.Controls.Add(lblSubtitle)

    ' Config status
    Dim lblCfgStatus As New System.Windows.Forms.Label
    lblCfgStatus.Font     = fSub
    lblCfgStatus.Location = New System.Drawing.Point(20, 62)
    lblCfgStatus.Size     = New System.Drawing.Size(576, 16)
    If configLoaded Then
        lblCfgStatus.Text      = "Učitana postojeća konfiguracija / Existing configuration loaded"
        lblCfgStatus.ForeColor = cGreen
    Else
        lblCfgStatus.Text      = "Nova konfiguracija / New configuration"
        lblCfgStatus.ForeColor = cSub
    End If
    dlg.Controls.Add(lblCfgStatus)

    ' Separator 1
    Dim sep1 As New System.Windows.Forms.Label
    sep1.BackColor = cSurface
    sep1.Location  = New System.Drawing.Point(20, 94)
    sep1.Size      = New System.Drawing.Size(576, 1)
    dlg.Controls.Add(sep1)

    ' ── Scrollable checkbox panel ─────────────────────────────────
    Dim scrollPanel As New System.Windows.Forms.Panel
    scrollPanel.BackColor  = cBg
    scrollPanel.AutoScroll = True
    scrollPanel.Location   = New System.Drawing.Point(20, 102)
    scrollPanel.Size       = New System.Drawing.Size(576, 486)
    dlg.Controls.Add(scrollPanel)

    Dim checkBoxes   As New System.Collections.Generic.List(Of System.Windows.Forms.CheckBox)
    Dim innerY       As Integer = 6
    Dim lastCategory As String  = ""

    For Each op As String() In allOps
        ' op(0)=id  op(1)=name  op(2)=category  op(3)=description
        If op(2) <> lastCategory Then
            Dim lblCat As New System.Windows.Forms.Label
            lblCat.Text      = op(2).ToUpper()
            lblCat.Font      = New System.Drawing.Font("Segoe UI", 8, System.Drawing.FontStyle.Bold)
            lblCat.ForeColor = cAmber
            lblCat.BackColor = cBg
            lblCat.Location  = New System.Drawing.Point(6, innerY)
            lblCat.Size      = New System.Drawing.Size(548, 16)
            scrollPanel.Controls.Add(lblCat)
            innerY       += 20
            lastCategory  = op(2)
        End If

        Dim chk As New System.Windows.Forms.CheckBox
        chk.Text      = op(0) & "   " & op(1)
        chk.Font      = New System.Drawing.Font("Consolas", 9)
        chk.ForeColor = cText
        chk.BackColor = cBg
        chk.Tag       = op(0)
        chk.Checked   = preSelectedIds.Contains(op(0))
        chk.Location  = New System.Drawing.Point(14, innerY)
        chk.Size      = New System.Drawing.Size(548, 20)
        scrollPanel.Controls.Add(chk)
        checkBoxes.Add(chk)
        innerY += 22

        Dim lblDesc As New System.Windows.Forms.Label
        lblDesc.Text      = op(3)
        lblDesc.Font      = New System.Drawing.Font("Segoe UI", 7)
        lblDesc.ForeColor = cSub
        lblDesc.BackColor = cBg
        lblDesc.Location  = New System.Drawing.Point(30, innerY)
        lblDesc.Size      = New System.Drawing.Size(530, 14)
        scrollPanel.Controls.Add(lblDesc)
        innerY += 18
    Next

    ' Separator 2
    Dim sep2 As New System.Windows.Forms.Label
    sep2.BackColor = cSurface
    sep2.Location  = New System.Drawing.Point(20, 596)
    sep2.Size      = New System.Drawing.Size(576, 1)
    dlg.Controls.Add(sep2)

    ' Cancel
    Dim btnCancel As New System.Windows.Forms.Button
    btnCancel.Text      = "Odustani / Cancel"
    btnCancel.Font      = fUI
    btnCancel.BackColor = cSurface : btnCancel.ForeColor = cSub
    btnCancel.FlatStyle = System.Windows.Forms.FlatStyle.Flat
    btnCancel.FlatAppearance.BorderColor = cSurface
    btnCancel.Location     = New System.Drawing.Point(110, 610)
    btnCancel.Size         = New System.Drawing.Size(160, 34)
    btnCancel.DialogResult = System.Windows.Forms.DialogResult.Cancel
    dlg.Controls.Add(btnCancel)

    ' Confirm
    Dim btnConfirm As New System.Windows.Forms.Button
    btnConfirm.Text      = "Potvrdi / Confirm"
    btnConfirm.Font      = fBold
    btnConfirm.BackColor = cAccent : btnConfirm.ForeColor = cText
    btnConfirm.FlatStyle = System.Windows.Forms.FlatStyle.Flat
    btnConfirm.FlatAppearance.BorderColor = cAccent
    btnConfirm.Location     = New System.Drawing.Point(346, 610)
    btnConfirm.Size         = New System.Drawing.Size(160, 34)
    btnConfirm.DialogResult = System.Windows.Forms.DialogResult.OK
    dlg.Controls.Add(btnConfirm)

    dlg.AcceptButton = btnConfirm
    dlg.CancelButton = btnCancel

    If dlg.ShowDialog() <> System.Windows.Forms.DialogResult.OK Then GoTo Cleanup

    ' ── Collect selected operations ───────────────────────────────
    ' Build id→op lookup so we can retrieve name/category for JSON output.
    Dim opById As New System.Collections.Generic.Dictionary(Of String, String())( _
        System.StringComparer.OrdinalIgnoreCase)
    For Each op As String() In allOps
        If Not opById.ContainsKey(op(0)) Then opById(op(0)) = op
    Next

    Dim selectedOps As New System.Collections.Generic.List(Of String())
    For Each chk As System.Windows.Forms.CheckBox In checkBoxes
        If chk.Checked Then
            Dim id As String = CStr(chk.Tag)
            If opById.ContainsKey(id) Then selectedOps.Add(opById(id))
        End If
    Next

    ' ── Write ppm_operations_config.json ─────────────────────────
    Try
        Dim opLines As New System.Collections.Generic.List(Of String)
        For Each op As String() In selectedOps
            opLines.Add("    { ""id"": """ & op(0) & _
                        """, ""name"": """ & op(1) & _
                        """, ""category"": """ & op(2) & """ }")
        Next

        Dim sb As New System.Text.StringBuilder
        sb.AppendLine("{")
        sb.AppendLine("  ""org"": ""STIRG"",")
        sb.AppendLine("  ""generated"": """ & DateTime.Now.ToString("yyyy-MM-ddTHH:mm:ss") & """,")
        sb.AppendLine("  ""operations"": [")
        If opLines.Count > 0 Then
            sb.AppendLine(String.Join("," & vbCrLf, opLines.ToArray()))
        End If
        sb.AppendLine("  ]")
        sb.Append("}")

        System.IO.File.WriteAllText(ORG_CONFIG_PATH, sb.ToString(), System.Text.Encoding.UTF8)
    Catch ex As Exception
        ShowError("Greška pri pisanju konfiguracije:" & vbCrLf & _
                  "Error writing org config:" & vbCrLf & vbCrLf & ex.Message)
        GoTo Cleanup
    End Try

    ShowSetupSummary(selectedOps.Count, allOps.Count, ORG_CONFIG_PATH)

Cleanup:
    fUI.Dispose() : fSub.Dispose() : fBold.Dispose()

End Sub

' ════════════════════════════════════════════════════════════════════
' SUBROUTINES
' ════════════════════════════════════════════════════════════════════

Sub ParseGlobalOps(content As String, _
                   ByRef ops As System.Collections.Generic.List(Of String()))
    ' Splits on "id": to isolate each JSON object.
    ' Produces String() {id, name, category, description} per entry.
    Dim parts() As String = content.Split( _
        New String() {"""id"""}, StringSplitOptions.RemoveEmptyEntries)
    For i As Integer = 1 To parts.Length - 1
        Dim seg  As String = parts(i)
        Dim id   As String = ExtractFirstQuotedValue(seg)
        Dim nm   As String = ExtractJsonField(seg, "name")
        Dim cat  As String = ExtractJsonField(seg, "category")
        Dim desc As String = ExtractJsonField(seg, "description")
        If id <> "" AndAlso nm <> "" Then
            ops.Add(New String() {id, nm, cat, desc})
        End If
    Next
End Sub

Sub ParseOrgConfigIds(content As String, _
                      ByRef ids As System.Collections.Generic.HashSet(Of String))
    ' Extracts id values from ppm_operations_config.json operations array.
    Dim parts() As String = content.Split( _
        New String() {"""id"""}, StringSplitOptions.RemoveEmptyEntries)
    For i As Integer = 1 To parts.Length - 1
        Dim id As String = ExtractFirstQuotedValue(parts(i))
        If id.StartsWith("OP-") Then ids.Add(id)
    Next
End Sub

Function ExtractFirstQuotedValue(s As String) As String
    ' Returns the first "..." value after the leading colon in s.
    Dim ci As Integer = s.IndexOf(":")
    If ci < 0 Then Return ""
    Dim q1 As Integer = s.IndexOf("""", ci)
    If q1 < 0 Then Return ""
    Dim q2 As Integer = s.IndexOf("""", q1 + 1)
    If q2 < 0 Then Return ""
    Return s.Substring(q1 + 1, q2 - q1 - 1)
End Function

Function ExtractJsonField(block As String, fieldName As String) As String
    ' Locates "fieldName" in block and returns its quoted value.
    Dim key As String = """" & fieldName & """"
    Dim ki  As Integer = block.IndexOf(key)
    If ki < 0 Then Return ""
    Dim ci  As Integer = block.IndexOf(":", ki + key.Length)
    If ci < 0 Then Return ""
    Dim q1  As Integer = block.IndexOf("""", ci + 1)
    If q1 < 0 Then Return ""
    Dim q2  As Integer = block.IndexOf("""", q1 + 1)
    If q2 < 0 Then Return ""
    Return block.Substring(q1 + 1, q2 - q1 - 1)
End Function

Sub ShowSetupSummary(nSelected As Integer, nTotal As Integer, configPath As String)
    Dim cBg      As System.Drawing.Color = System.Drawing.Color.FromArgb(59, 68, 83)
    Dim cSurface As System.Drawing.Color = System.Drawing.Color.FromArgb(72, 82, 98)
    Dim cAccent  As System.Drawing.Color = System.Drawing.Color.FromArgb(46, 125, 209)
    Dim cText    As System.Drawing.Color = System.Drawing.Color.FromArgb(230, 237, 243)
    Dim cSub     As System.Drawing.Color = System.Drawing.Color.FromArgb(180, 190, 200)
    Dim cGreen   As System.Drawing.Color = System.Drawing.Color.FromArgb(63, 185, 80)

    Dim sf As New System.Windows.Forms.Form
    sf.Text            = "PPM - Konfiguracija sačuvana / Configuration Saved"
    sf.Size            = New System.Drawing.Size(480, 230)
    sf.StartPosition   = System.Windows.Forms.FormStartPosition.CenterScreen
    sf.FormBorderStyle = System.Windows.Forms.FormBorderStyle.FixedDialog
    sf.BackColor       = cBg : sf.MaximizeBox = False
    sf.AutoScaleMode   = System.Windows.Forms.AutoScaleMode.None

    Dim lblT As New System.Windows.Forms.Label
    lblT.Text      = "KONFIGURACIJA SAČUVANA / CONFIGURATION SAVED"
    lblT.Font      = New System.Drawing.Font("Segoe UI", 9, System.Drawing.FontStyle.Bold)
    lblT.ForeColor = cAccent
    lblT.Location  = New System.Drawing.Point(20, 20)
    lblT.Size      = New System.Drawing.Size(440, 18)
    sf.Controls.Add(lblT)

    Dim lblCount As New System.Windows.Forms.Label
    lblCount.Text      = nSelected & " od " & nTotal & " operacija izabrano / " & _
                         nSelected & " of " & nTotal & " operations selected"
    lblCount.Font      = New System.Drawing.Font("Segoe UI", 9)
    lblCount.ForeColor = cGreen
    lblCount.Location  = New System.Drawing.Point(20, 46)
    lblCount.Size      = New System.Drawing.Size(440, 18)
    sf.Controls.Add(lblCount)

    Dim lblPath As New System.Windows.Forms.Label
    lblPath.Text      = configPath
    lblPath.Font      = New System.Drawing.Font("Consolas", 7)
    lblPath.ForeColor = cSub
    lblPath.Location  = New System.Drawing.Point(20, 70)
    lblPath.Size      = New System.Drawing.Size(440, 14)
    sf.Controls.Add(lblPath)

    Dim lblNote As New System.Windows.Forms.Label
    lblNote.Text      = "Pokrenite PPM Mark Operations na svakom dijelu ili sklopu." & vbCrLf & _
                        "Run PPM Mark Operations on each part or assembly."
    lblNote.Font      = New System.Drawing.Font("Segoe UI", 8)
    lblNote.ForeColor = cSub
    lblNote.Location  = New System.Drawing.Point(20, 90)
    lblNote.Size      = New System.Drawing.Size(440, 32)
    sf.Controls.Add(lblNote)

    Dim sep As New System.Windows.Forms.Label
    sep.BackColor = cSurface
    sep.Location  = New System.Drawing.Point(20, 132)
    sep.Size      = New System.Drawing.Size(440, 1)
    sf.Controls.Add(sep)

    Dim btnOK As New System.Windows.Forms.Button
    btnOK.Text      = "OK"
    btnOK.Font      = New System.Drawing.Font("Segoe UI", 9, System.Drawing.FontStyle.Bold)
    btnOK.BackColor = cAccent : btnOK.ForeColor = cText
    btnOK.FlatStyle = System.Windows.Forms.FlatStyle.Flat
    btnOK.FlatAppearance.BorderColor = cAccent
    btnOK.Location     = New System.Drawing.Point(180, 148)
    btnOK.Size         = New System.Drawing.Size(120, 32)
    btnOK.DialogResult = System.Windows.Forms.DialogResult.OK
    sf.Controls.Add(btnOK)
    sf.AcceptButton = btnOK : sf.ShowDialog()
End Sub

Sub ShowError(msg As String)
    Dim ef As New System.Windows.Forms.Form
    ef.Text            = "PPM - Greška / Error"
    ef.Size            = New System.Drawing.Size(460, 200)
    ef.StartPosition   = System.Windows.Forms.FormStartPosition.CenterScreen
    ef.FormBorderStyle = System.Windows.Forms.FormBorderStyle.FixedDialog
    ef.BackColor       = System.Drawing.Color.FromArgb(59, 68, 83) : ef.MaximizeBox = False
    ef.AutoScaleMode   = System.Windows.Forms.AutoScaleMode.None
    Dim lbl As New System.Windows.Forms.Label
    lbl.Text      = msg
    lbl.Font      = New System.Drawing.Font("Segoe UI", 9)
    lbl.ForeColor = System.Drawing.Color.FromArgb(210, 153, 34)
    lbl.Location  = New System.Drawing.Point(20, 20) : lbl.Size = New System.Drawing.Size(420, 80)
    ef.Controls.Add(lbl)
    Dim btn As New System.Windows.Forms.Button
    btn.Text      = "OK"
    btn.Font      = New System.Drawing.Font("Segoe UI", 9, System.Drawing.FontStyle.Bold)
    btn.BackColor = System.Drawing.Color.FromArgb(46, 125, 209)
    btn.ForeColor = System.Drawing.Color.FromArgb(230, 237, 243)
    btn.FlatStyle = System.Windows.Forms.FlatStyle.Flat
    btn.Location  = New System.Drawing.Point(180, 134) : btn.Size = New System.Drawing.Size(100, 32)
    btn.DialogResult = System.Windows.Forms.DialogResult.OK
    ef.Controls.Add(btn) : ef.AcceptButton = btn : ef.ShowDialog()
End Sub
