' PPM_MarkOperations.iLogicVb
' Marks manufacturing operations on the active part or assembly.
' Reads ppm_operations_config.json, shows tagged checklist,
' writes PPM_OP_XXXXX iProperties to the document's Custom property set.
' Auto-populate: sheet metal/bend detection for parts; weldment detection for assemblies.

AddReference "System.Drawing"
AddReference "System.Windows.Forms"

Sub Main()

    ' ── Auto-update check ────────────────────────────────────────
    Dim localPath   As String = "C:\PPM Cuts and Bends\iLogic\PPM_MarkOperations.iLogicVb"
    Dim networkPath As String = "X:\USER\Gavrilović\iLogic\PPM_MarkOperations.iLogicVb"
    Try
        If System.IO.File.Exists(networkPath) AndAlso System.IO.File.Exists(localPath) Then
            Dim netTime   As DateTime = System.IO.File.GetLastWriteTime(networkPath)
            Dim localTime As DateTime = System.IO.File.GetLastWriteTime(localPath)
            If netTime > localTime Then
                System.IO.File.Copy(networkPath, localPath, True)
                System.Windows.Forms.MessageBox.Show( _
                    "Nova verzija je instalirana." & vbCrLf & _
                    "New version installed." & vbCrLf & vbCrLf & _
                    "Pokrenite makro ponovo." & vbCrLf & _
                    "Please run the macro again.", _
                    "PPM - Azuriranje / Update", _
                    System.Windows.Forms.MessageBoxButtons.OK, _
                    System.Windows.Forms.MessageBoxIcon.Information)
                Exit Sub
            End If
        End If
    Catch : End Try
    ' ─────────────────────────────────────────────────────────────

    ' ── Palette (D-258) ──────────────────────────────────────────
    Dim cBg      As System.Drawing.Color = System.Drawing.Color.FromArgb(59, 68, 83)
    Dim cSurface As System.Drawing.Color = System.Drawing.Color.FromArgb(72, 82, 98)
    Dim cAccent  As System.Drawing.Color = System.Drawing.Color.FromArgb(46, 125, 209)
    Dim cText    As System.Drawing.Color = System.Drawing.Color.FromArgb(230, 237, 243)
    Dim cSub     As System.Drawing.Color = System.Drawing.Color.FromArgb(180, 190, 200)
    Dim cGreen   As System.Drawing.Color = System.Drawing.Color.FromArgb(63, 185, 80)
    Dim cAmber   As System.Drawing.Color = System.Drawing.Color.FromArgb(210, 153, 34)

    Dim fUI   As New System.Drawing.Font("Segoe UI", 9)
    Dim fSub  As New System.Drawing.Font("Segoe UI", 8)
    Dim fBold As New System.Drawing.Font("Segoe UI", 9, System.Drawing.FontStyle.Bold)

    ' ── Path ─────────────────────────────────────────────────────
    Const ORG_CONFIG_PATH As String = "X:\USER\Gavrilović\iLogic\config\ppm_operations_config.json"

    ' ── Guard: part or assembly only ─────────────────────────────
    Dim isAssembly As Boolean = False
    Dim oDoc       As Inventor.Document = Nothing

    If TypeOf ThisApplication.ActiveDocument Is PartDocument Then
        oDoc = ThisApplication.ActiveDocument
    ElseIf TypeOf ThisApplication.ActiveDocument Is AssemblyDocument Then
        oDoc       = ThisApplication.ActiveDocument
        isAssembly = True
    Else
        ShowError("Otvori deo (.ipt) ili sklop (.iam) pre pokretanja makroa." & vbCrLf & _
                  "Open a part (.ipt) or assembly (.iam) before running this macro.")
        GoTo Cleanup
    End If

    ' ── Multi-select detection (NEW) ────────────────────────────
    ' If running from an assembly with 2+ occurrences selected in the
    ' browser (Ctrl/Shift-click), resolve each to its underlying
    ' document, dedupe (multiple instances of the same part collapse
    ' to one target -- iProperties are per-document, so marking one
    ' instance already marks all instances of that file), and treat
    ' this as a batch operation across all of them. Any other case
    ' (single part open, assembly with 0 or 1 selected) behaves
    ' EXACTLY as before -- targetDocs is just {oDoc}, zero behavior
    ' change to the proven single-document flow.
    ' NOT YET LIVE-TESTED -- Document.SelectSet confirmed real via
    ' multiple independent Autodesk Community/blog sources, but this
    ' specific usage (multi-item iteration, ComponentOccurrence
    ' filtering, dedup) has not been run against a real Inventor
    ' session yet.
    Dim multiSelectMode As Boolean = False
    Dim targetDocs As New System.Collections.Generic.List(Of Inventor.Document)

    If isAssembly Then
        Try
            If oDoc.SelectSet.Count > 1 Then
                Dim seenPaths As New System.Collections.Generic.HashSet(Of String)( _
                    System.StringComparer.OrdinalIgnoreCase)
                For i As Integer = 1 To oDoc.SelectSet.Count
                    Try
                        Dim selItem As Object = oDoc.SelectSet.Item(i)
                        If TypeOf selItem Is ComponentOccurrence Then
                            Dim oSelOcc As ComponentOccurrence = CType(selItem, ComponentOccurrence)
                            Dim oTargetDoc As Inventor.Document = oSelOcc.Definition.Document
                            Dim tPath As String = oTargetDoc.FullFileName
                            If Not seenPaths.Contains(tPath) Then
                                seenPaths.Add(tPath)
                                targetDocs.Add(oTargetDoc)
                            End If
                        End If
                    Catch
                        ' one bad selection item shouldn't abort the batch
                    End Try
                Next
                If targetDocs.Count > 1 Then multiSelectMode = True
            End If
        Catch
            ' SelectSet unavailable for some reason -- fall through to
            ' normal single-document mode below
        End Try
    End If

    If Not multiSelectMode Then
        targetDocs.Clear()
        targetDocs.Add(oDoc)
    End If

    ' ── Visual confirmation of resolved selection (NEW) ───────────
    ' "N selected parts" alone isn't enough to trust before a batch
    ' write -- show exactly which parts were resolved, with a chance
    ' to back out if the selection resolved to something unexpected
    ' (e.g. more/fewer parts than intended, wrong parts due to a
    ' dedup surprise). Only shown in multi-select mode; single-part
    ' mode is unchanged since there's nothing to confirm.
    If multiSelectMode Then
        Dim confirmLines As New System.Collections.Generic.List(Of String)
        For Each dTarget As Inventor.Document In targetDocs
            Dim dPn As String = ""
            Try
                Dim dProp As Inventor.Property = _
                    dTarget.PropertySets.Item("Design Tracking Properties").Item("Part Number")
                dPn = CStr(dProp.Value).Trim()
            Catch : End Try
            If dPn = "" Then
                Try : dPn = System.IO.Path.GetFileNameWithoutExtension(dTarget.FullFileName)
                Catch : dPn = "(unknown)" : End Try
            End If
            confirmLines.Add("• " & dPn)
        Next

        Dim confirmMsg As String = "Sledeći delovi će biti grupno označeni / " & _
            "The following parts will be batch-marked (" & targetDocs.Count & "):" & _
            vbCrLf & vbCrLf & String.Join(vbCrLf, confirmLines) & _
            vbCrLf & vbCrLf & "Nastaviti? / Continue?"

        Dim confirmResult = System.Windows.Forms.MessageBox.Show( _
            confirmMsg, "PPM - Potvrdi izbor / Confirm Selection", _
            System.Windows.Forms.MessageBoxButtons.YesNo, _
            System.Windows.Forms.MessageBoxIcon.Question)

        If confirmResult <> System.Windows.Forms.DialogResult.Yes Then
            GoTo Cleanup
        End If
    End If

    ' ── Read part number ─────────────────────────────────────────
    Dim pn As String = ""
    If multiSelectMode Then
        pn = targetDocs.Count & " selected parts"
    Else
        Try
            Dim oProp As Inventor.Property = _
                oDoc.PropertySets.Item("Design Tracking Properties").Item("Part Number")
            pn = CStr(oProp.Value).Trim()
        Catch : End Try
        If pn = "" Then
            Try : pn = System.IO.Path.GetFileNameWithoutExtension(oDoc.FullFileName)
            Catch : pn = "UNKNOWN" : End Try
        End If
    End If

    ' ── Load org config ───────────────────────────────────────────
    ' Each entry parsed into String() {id, name, category}
    If Not System.IO.File.Exists(ORG_CONFIG_PATH) Then
        ShowError("Pokrenite PPM Operations Setup prvo." & vbCrLf & _
                  "Run PPM Operations Setup first." & vbCrLf & vbCrLf & ORG_CONFIG_PATH)
        GoTo Cleanup
    End If

    Dim orgOps As New System.Collections.Generic.List(Of String())
    Try
        Dim raw As String = System.IO.File.ReadAllText(ORG_CONFIG_PATH, System.Text.Encoding.UTF8)
        ParseOrgOps(raw, orgOps)
    Catch ex As Exception
        ShowError("Greška pri čitanju org konfiguracije:" & vbCrLf & _
                  "Error reading org config:" & vbCrLf & vbCrLf & ex.Message)
        GoTo Cleanup
    End Try

    If orgOps.Count = 0 Then
        ShowError("Org konfiguracija je prazna. Pokrenite PPM Operations Setup." & vbCrLf & _
                  "Org config is empty. Run PPM Operations Setup.")
        GoTo Cleanup
    End If

    ' ── Read existing PPM iProperties ────────────────────────────
    ' Pre-check any op already written as value=1. In multi-select
    ' mode, an op is only pre-checked if it's =1 on EVERY selected
    ' document (the honest representation of "common state" across a
    ' batch) -- not just the first one. Single-document mode is
    ' UNCHANGED from the original.
    Dim existingIds As New System.Collections.Generic.HashSet(Of String)( _
        System.StringComparer.OrdinalIgnoreCase)
    If multiSelectMode Then
        For Each op As String() In orgOps
            Dim propName As String = "PPM_" & op(0).Replace("-", "_")
            Dim setOnAll As Boolean = True
            For Each dTarget As Inventor.Document In targetDocs
                Try
                    Dim oC As PropertySet = dTarget.PropertySets.Item("Inventor User Defined Properties")
                    If CInt(oC.Item(propName).Value) <> 1 Then setOnAll = False : Exit For
                Catch
                    setOnAll = False : Exit For
                End Try
            Next
            If setOnAll Then existingIds.Add(op(0))
        Next
    Else
        Try
            Dim oCustom As PropertySet = oDoc.PropertySets.Item("Inventor User Defined Properties")
            For Each op As String() In orgOps
                Dim propName As String = "PPM_" & op(0).Replace("-", "_")
                Try
                    If CInt(oCustom.Item(propName).Value) = 1 Then existingIds.Add(op(0))
                Catch : End Try
            Next
        Catch : End Try
    End If

    ' ── Auto-populate detection ───────────────────────────────────
    ' SKIPPED ENTIRELY in multi-select mode -- selected parts could be
    ' mixed types (sheet metal + machined, etc.), and merging
    ' per-part-type auto-detect logic across an arbitrary batch is not
    ' something to guess at safely. Multi-select mode is pure manual
    ' checklist based on common existing state (existingIds above) --
    ' no auto-detect surprises. Single-document mode is UNCHANGED --
    ' this just adds a new first branch to the existing If/ElseIf
    ' chain below; the part-detection and weldment-detection branches
    ' are untouched.
    Dim autoDetectedIds As New System.Collections.Generic.HashSet(Of String)( _
        System.StringComparer.OrdinalIgnoreCase)
    Dim isWeldment     As Boolean = False
    Dim configWarnings As New System.Collections.Generic.List(Of String)

    If multiSelectMode Then
        ' no auto-detect in batch mode -- see comment above
    ElseIf Not isAssembly Then
        ' ── Part: sheet metal + bend detection ───────────────────
        Dim oPart As PartDocument = CType(oDoc, PartDocument)

        If TypeOf oPart.ComponentDefinition Is SheetMetalComponentDefinition Then
            Dim oSMDef As SheetMetalComponentDefinition = _
                CType(oPart.ComponentDefinition, SheetMetalComponentDefinition)

            ' Sheet metal → Laser Cutting (OP-00003) and Deburring (OP-00013)
            For Each op As String() In orgOps
                If op(0) = "OP-00003" OrElse op(0) = "OP-00013" Then
                    autoDetectedIds.Add(op(0))
                End If
            Next

            ' ── Bend detection (2-step cascade) ──────────────────
            Dim bendCount    As Integer = 0
            Dim bendMethod   As String  = "none"
            Dim matchedNames As New System.Collections.Generic.List(Of String)

            ' Step 1: iterate Features, check name contains forming keyword (case-insensitive)
            Try
                Dim keywords() As String = {"flange", "fold", "bend", "hem", "roll"}
                For Each feat As Object In oSMDef.Features
                    Try
                        Dim featName As String = feat.Name
                        Dim lName    As String = LCase(featName)
                        For Each kw As String In keywords
                            If InStr(lName, kw) > 0 Then
                                matchedNames.Add(featName)
                                Exit For
                            End If
                        Next
                    Catch : End Try
                Next
                bendCount = matchedNames.Count
                If bendCount > 0 Then bendMethod = "feature name match"
            Catch : End Try

            ' Step 2: "Bend Count" from Design Tracking Properties
            If bendCount = 0 Then
                Try
                    Dim bendProp As Object = oDoc.PropertySets. _
                        Item("Design Tracking Properties").Item("Bend Count")
                    bendCount = CInt(bendProp.Value)
                    If bendCount > 0 Then bendMethod = "Design Tracking Properties"
                Catch : End Try
            End If

            If bendCount > 0 Then
                For Each op As String() In orgOps
                    If op(0) = "OP-00009" Then autoDetectedIds.Add(op(0)) : Exit For
                Next
                Dim bendOpFound As Boolean = False
                For Each op As String() In orgOps
                    Dim nm As String = LCase(op(1))
                    If InStr(nm, "flange") > 0 OrElse InStr(nm, "fold") > 0 OrElse InStr(nm, "bend") > 0 Then
                        bendOpFound = True : Exit For
                    End If
                Next
                If Not bendOpFound Then
                    configWarnings.Add("Savijanje detektovano ali operacija nije u konfiguraciji / Bending detected but no matching op in org config")
                End If
            End If

            ' Write detection result to PPM_BendDetect iProperty for diagnostics
            Dim bendDebugMsg As String
            If matchedNames.Count > 0 Then
                Dim nameList As String = String.Join(", ", matchedNames.ToArray())
                bendDebugMsg = "forming: " & matchedNames.Count & " matched [" & nameList & "] → flagged"
            ElseIf bendCount > 0 Then
                bendDebugMsg = "forming: " & bendCount & " matched [Design Tracking Properties] → flagged"
            Else
                bendDebugMsg = "forming: 0 matched → not flagged"
            End If
            Try
                Dim oPS As PropertySets = oDoc.PropertySets
                Dim oC  As PropertySet
                Try : oC = oPS.Item("Inventor User Defined Properties")
                Catch : oC = oPS.Add("Inventor User Defined Properties") : End Try
                Try : oC.Item("PPM_BendDetect").Value = bendDebugMsg
                Catch : Try : oC.Add(bendDebugMsg, "PPM_BendDetect") : Catch : End Try : End Try
            Catch : End Try
        End If

        ' ── Hole and thread detection ─────────────────────────────
        Dim plainCount       As Integer = 0
        Dim cboreCount       As Integer = 0
        Dim unknownHoleCount As Integer = 0
        Dim unknownTypes     As New System.Collections.Generic.Dictionary(Of Integer, Integer)
        Dim holeDiameters    As New System.Collections.Generic.List(Of String)

        Try
            For Each h As Object In oDoc.ComponentDefinition.Features.HoleFeatures
                Try
                    Dim ht  As Integer = CInt(h.HoleType)
                    Dim dia As String  = ""
                    Try
                        Dim dVal As Double = h.HoleDiameter.Value
                        dia = Math.Round(dVal * 10, 1).ToString() & "mm"
                    Catch : End Try
                    Select Case ht
                        Case 21505
                            plainCount += 1
                            If dia <> "" Then holeDiameters.Add("D" & dia)
                        Case 21506
                            cboreCount += 1
                        Case Else
                            unknownHoleCount += 1
                            If unknownTypes.ContainsKey(ht) Then
                                unknownTypes(ht) += 1
                            Else
                                unknownTypes.Add(ht, 1)
                            End If
                    End Select
                Catch : End Try
            Next
        Catch : End Try

        Dim threadCount  As Integer = 0
        Dim threadCounts As New System.Collections.Generic.Dictionary(Of String, Integer)( _
            System.StringComparer.OrdinalIgnoreCase)
        Try
            For Each t As Object In oDoc.ComponentDefinition.Features.ThreadFeatures
                Try
                    threadCount += 1
                    Try
                        Dim desig As String = t.ThreadInfo.ThreadDesignation
                        If threadCounts.ContainsKey(desig) Then
                            threadCounts(desig) += 1
                        Else
                            threadCounts.Add(desig, 1)
                        End If
                    Catch : End Try
                Catch : End Try
            Next
        Catch : End Try

        Dim totalHoles As Integer = plainCount + cboreCount + unknownHoleCount
        If (plainCount + unknownHoleCount) > 0 Then
            For Each op As String() In orgOps
                If InStr(LCase(op(1)), "drill") > 0 Then autoDetectedIds.Add(op(0)) : Exit For
            Next
        End If
        If cboreCount > 0 Then
            For Each op As String() In orgOps
                Dim nm As String = LCase(op(1))
                If InStr(nm, "countersink") > 0 OrElse InStr(nm, "counterbor") > 0 Then
                    autoDetectedIds.Add(op(0)) : Exit For
                End If
            Next
        End If
        If threadCount > 0 Then
            For Each op As String() In orgOps
                Dim nm As String = LCase(op(1))
                If InStr(nm, "tap") > 0 OrElse InStr(nm, "thread") > 0 Then
                    autoDetectedIds.Add(op(0)) : Exit For
                End If
            Next
        End If

        ' Check for unmatched detections
        If totalHoles > 0 Then
            Dim drillOpFound As Boolean = False
            For Each op As String() In orgOps
                If InStr(LCase(op(1)), "drill") > 0 Then drillOpFound = True : Exit For
            Next
            If Not drillOpFound Then
                configWarnings.Add("Rupe detektovane ali operacija nije u konfiguraciji / Holes detected but no Drilling op in org config")
            End If
        End If
        If threadCount > 0 Then
            Dim tapOpFound As Boolean = False
            For Each op As String() In orgOps
                Dim nm As String = LCase(op(1))
                If InStr(nm, "tap") > 0 OrElse InStr(nm, "thread") > 0 Then tapOpFound = True : Exit For
            Next
            If Not tapOpFound Then
                configWarnings.Add("Navoji detektovani ali operacija nije u konfiguraciji / Threads detected but no Tapping op in org config")
            End If
        End If

        ' Build PPM_Holes summary
        Dim holeParts As New System.Collections.Generic.List(Of String)
        If plainCount > 0 Then holeParts.Add(plainCount & "x plain")
        If cboreCount > 0 Then holeParts.Add(cboreCount & "x cbore")
        For Each kvp As System.Collections.Generic.KeyValuePair(Of Integer, Integer) In unknownTypes
            holeParts.Add(kvp.Value & "x unknown(" & kvp.Key & ")")
        Next
        Dim holeMsg As String = If(holeParts.Count > 0, String.Join(", ", holeParts.ToArray()), "")

        ' Build PPM_Threads summary
        Dim threadMsg As String = ""
        If threadCount > 0 Then
            Dim tParts As New System.Collections.Generic.List(Of String)
            For Each kvp As System.Collections.Generic.KeyValuePair(Of String, Integer) In threadCounts
                tParts.Add(kvp.Key & " x" & kvp.Value)
            Next
            threadMsg = String.Join(", ", tParts.ToArray())
        End If

        Try
            Dim oPS As PropertySets = oDoc.PropertySets
            Dim oC  As PropertySet
            Try : oC = oPS.Item("Inventor User Defined Properties")
            Catch : oC = oPS.Add("Inventor User Defined Properties") : End Try
            Try : oC.Item("PPM_Holes").Value = holeMsg
            Catch : Try : oC.Add(holeMsg, "PPM_Holes") : Catch : End Try : End Try
            Try : oC.Item("PPM_Threads").Value = threadMsg
            Catch : Try : oC.Add(threadMsg, "PPM_Threads") : Catch : End Try : End Try
        Catch : End Try

    ElseIf TypeOf oDoc.ComponentDefinition Is WeldmentComponentDefinition Then
        ' ── Assembly: weldment detection ──────────────────────────
        ' Only flag as weldment if THIS document has weld features directly
        ' on it (Welds.Count > 0), not inherited from sub-assemblies.
        Dim oWeldDef  As WeldmentComponentDefinition = _
            CType(oDoc.ComponentDefinition, WeldmentComponentDefinition)
        Dim weldCount As Integer = 0
        Try : weldCount = oWeldDef.Welds.Count : Catch : End Try
        If weldCount > 0 Then isWeldment = True
        If isWeldment Then
            Dim weldOpFound As Boolean = False
            For Each op As String() In orgOps
                If InStr(LCase(op(1)), "weld") > 0 Then weldOpFound = True : Exit For
            Next
            If Not weldOpFound Then
                configWarnings.Add("Zavarena konstr. detektovana ali operacija nije u konfiguraciji / Weldment detected but no Joining op in org config")
            End If
        End If
        ' isWeldment = False → plain assembly, no auto-populate
    End If

    ' ── Compute form geometry ─────────────────────────────────────
    ' Assembly warning row shifts the scroll panel down by 20px.
    Dim panelTop As Integer = If(isAssembly, 122, 102)
    Dim panelH   As Integer = 420
    Dim sep2Y    As Integer = panelTop + panelH + 8
    Const MARGIN As Integer = 20
    Dim btnRowY  As Integer = sep2Y + 14
    Dim formH    As Integer = sep2Y + 1 + MARGIN + 34 + MARGIN
    If formH < 660 Then formH = 660

    ' ── Tagging dialog ────────────────────────────────────────────
    Dim dlg As New System.Windows.Forms.Form
    dlg.Text            = "PPM - Označi operacije / Mark Operations"
    dlg.Size            = New System.Drawing.Size(620, formH)
    dlg.StartPosition   = System.Windows.Forms.FormStartPosition.CenterScreen
    dlg.FormBorderStyle = System.Windows.Forms.FormBorderStyle.FixedDialog
    dlg.BackColor       = cBg
    dlg.MaximizeBox     = False : dlg.MinimizeBox = False
    dlg.AutoScaleMode   = System.Windows.Forms.AutoScaleMode.None

    ' Title
    Dim lblTitle As New System.Windows.Forms.Label
    lblTitle.Text      = "OZNAČI OPERACIJE / MARK OPERATIONS"
    lblTitle.Font      = New System.Drawing.Font("Segoe UI", 10, System.Drawing.FontStyle.Bold)
    lblTitle.ForeColor = cAccent
    lblTitle.Location  = New System.Drawing.Point(20, 16)
    lblTitle.Size      = New System.Drawing.Size(576, 20)
    dlg.Controls.Add(lblTitle)

    ' Part number — Consolas green, same pattern as single-export macro
    Dim lblPN As New System.Windows.Forms.Label
    lblPN.Text      = pn
    lblPN.Font      = New System.Drawing.Font("Consolas", 11, System.Drawing.FontStyle.Bold)
    lblPN.ForeColor = cGreen
    lblPN.Location  = New System.Drawing.Point(20, 40)
    lblPN.Size      = New System.Drawing.Size(576, 22)
    dlg.Controls.Add(lblPN)

    ' Document type
    Dim lblDocType As New System.Windows.Forms.Label
    If multiSelectMode Then
        lblDocType.Text = "GRUPNO OZNAČAVANJE / BATCH MODE — auto-detekcija isključena / auto-detect disabled"
    Else
        lblDocType.Text = If(isAssembly, "SKLOP / ASSEMBLY", "DEO / PART")
    End If
    lblDocType.Font      = fSub
    lblDocType.ForeColor = cSub
    lblDocType.Location  = New System.Drawing.Point(20, 66)
    lblDocType.Size      = New System.Drawing.Size(576, 16)
    dlg.Controls.Add(lblDocType)

    ' Assembly / weldment notice
    If isAssembly Then
        Dim lblAsmNote As New System.Windows.Forms.Label
        If isWeldment Then
            lblAsmNote.Text      = "Zavarena konstr. — izaberite tip zavarivanja / Weldment detected — select welding type(s) from Joining below"
            lblAsmNote.ForeColor = cGreen
        Else
            lblAsmNote.Text      = "Automatsko popunjavanje nije dostupno za sklopove / Auto-populate not available for assemblies"
            lblAsmNote.ForeColor = cAmber
        End If
        lblAsmNote.Font     = New System.Drawing.Font("Segoe UI", 8)
        lblAsmNote.Location = New System.Drawing.Point(20, 86)
        lblAsmNote.Size     = New System.Drawing.Size(576, 16)
        dlg.Controls.Add(lblAsmNote)

    End If

    ' Separator 1
    Dim sep1 As New System.Windows.Forms.Label
    sep1.BackColor = cSurface
    sep1.Location  = New System.Drawing.Point(20, panelTop - 8)
    sep1.Size      = New System.Drawing.Size(576, 1)
    dlg.Controls.Add(sep1)

    ' ── Scrollable checkbox panel ─────────────────────────────────
    Dim scrollPanel As New System.Windows.Forms.Panel
    scrollPanel.BackColor  = cBg
    scrollPanel.AutoScroll = True
    scrollPanel.Location   = New System.Drawing.Point(20, panelTop)
    scrollPanel.Size       = New System.Drawing.Size(576, panelH)
    dlg.Controls.Add(scrollPanel)

    Dim checkBoxes   As New System.Collections.Generic.List(Of System.Windows.Forms.CheckBox)
    Dim innerY       As Integer = 6
    Dim lastCategory As String  = ""
    Dim joiningY     As Integer = 0

    For Each warn As String In configWarnings
        Dim lblWarn As New System.Windows.Forms.Label
        lblWarn.Text      = warn
        lblWarn.Font      = fSub
        lblWarn.ForeColor = cAmber
        lblWarn.BackColor = cBg
        lblWarn.Location  = New System.Drawing.Point(6, innerY)
        lblWarn.Size      = New System.Drawing.Size(548, 14)
        scrollPanel.Controls.Add(lblWarn)
        innerY += 16
    Next
    If configWarnings.Count > 0 Then innerY += 6

    For Each op As String() In orgOps
        ' op(0)=id  op(1)=name  op(2)=category
        If op(2) <> lastCategory Then
            If isWeldment AndAlso op(2) = "Joining" Then joiningY = innerY
            Dim lblCat As New System.Windows.Forms.Label
            lblCat.Text      = op(2).ToUpper()
            lblCat.Font      = New System.Drawing.Font("Segoe UI", 8, System.Drawing.FontStyle.Bold)
            lblCat.ForeColor = If(isWeldment AndAlso op(2) = "Joining", cGreen, cAmber)
            lblCat.BackColor = cBg
            lblCat.Location  = New System.Drawing.Point(6, innerY)
            lblCat.Size      = New System.Drawing.Size(548, 16)
            scrollPanel.Controls.Add(lblCat)
            innerY       += 20
            lastCategory  = op(2)
        End If

        Dim isAuto       As Boolean = autoDetectedIds.Contains(op(0))
        Dim isPreChecked As Boolean = existingIds.Contains(op(0)) OrElse isAuto

        Dim chkText As String = op(0) & "   " & op(1)
        If isAuto Then chkText &= "   [auto]"

        Dim chk As New System.Windows.Forms.CheckBox
        chk.Text      = chkText
        chk.Font      = New System.Drawing.Font("Consolas", 9)
        chk.ForeColor = If(isAuto, cGreen, cText)
        chk.BackColor = cBg
        chk.Tag       = op(0)
        chk.Checked   = isPreChecked
        chk.Location  = New System.Drawing.Point(14, innerY)
        chk.Size      = New System.Drawing.Size(548, 20)
        scrollPanel.Controls.Add(chk)
        checkBoxes.Add(chk)
        innerY += 22

        ' Description is not stored in org config — show category as context
        Dim lblDesc As New System.Windows.Forms.Label
        lblDesc.Text      = op(2)
        lblDesc.Font      = New System.Drawing.Font("Segoe UI", 7)
        lblDesc.ForeColor = cSub
        lblDesc.BackColor = cBg
        lblDesc.Location  = New System.Drawing.Point(30, innerY)
        lblDesc.Size      = New System.Drawing.Size(530, 14)
        scrollPanel.Controls.Add(lblDesc)
        innerY += 18
    Next

    If isWeldment Then
        scrollPanel.AutoScrollPosition = New System.Drawing.Point(0, Math.Max(0, joiningY - 10))
    End If

    ' Separator 2
    Dim sep2 As New System.Windows.Forms.Label
    sep2.BackColor = cSurface
    sep2.Location  = New System.Drawing.Point(20, sep2Y)
    sep2.Size      = New System.Drawing.Size(576, 1)
    dlg.Controls.Add(sep2)

    ' More Ops shortcut — guides user to run Operations Setup separately
    Dim btnSetup As New System.Windows.Forms.Button
    btnSetup.Text      = "Vise operacija / More Ops"
    btnSetup.Font      = fSub
    btnSetup.BackColor = cSurface : btnSetup.ForeColor = cSub
    btnSetup.FlatStyle = System.Windows.Forms.FlatStyle.Flat
    btnSetup.FlatAppearance.BorderColor = cSurface
    btnSetup.Location     = New System.Drawing.Point(20, btnRowY)
    btnSetup.Size         = New System.Drawing.Size(150, 34)
    btnSetup.DialogResult = System.Windows.Forms.DialogResult.Retry
    dlg.Controls.Add(btnSetup)

    ' Cancel
    Dim btnCancel As New System.Windows.Forms.Button
    btnCancel.Text      = "Odustani / Cancel"
    btnCancel.Font      = fUI
    btnCancel.BackColor = cSurface : btnCancel.ForeColor = cSub
    btnCancel.FlatStyle = System.Windows.Forms.FlatStyle.Flat
    btnCancel.FlatAppearance.BorderColor = cSurface
    btnCancel.Location     = New System.Drawing.Point(200, btnRowY)
    btnCancel.Size         = New System.Drawing.Size(150, 34)
    btnCancel.DialogResult = System.Windows.Forms.DialogResult.Cancel
    dlg.Controls.Add(btnCancel)

    ' Confirm — right edge at 596px, flush with scroll panel
    Dim btnConfirm As New System.Windows.Forms.Button
    btnConfirm.Text      = "Potvrdi / Confirm"
    btnConfirm.Font      = fBold
    btnConfirm.BackColor = cAccent : btnConfirm.ForeColor = cText
    btnConfirm.FlatStyle = System.Windows.Forms.FlatStyle.Flat
    btnConfirm.FlatAppearance.BorderColor = cAccent
    btnConfirm.Location     = New System.Drawing.Point(426, btnRowY)
    btnConfirm.Size         = New System.Drawing.Size(170, 34)
    btnConfirm.DialogResult = System.Windows.Forms.DialogResult.OK
    dlg.Controls.Add(btnConfirm)

    dlg.AcceptButton = btnConfirm
    dlg.CancelButton = btnCancel

    dlg.ShowDialog()
    If dlg.DialogResult = System.Windows.Forms.DialogResult.Retry Then
        System.Windows.Forms.MessageBox.Show( _
            "Zatvorite ovaj dijalog i pokrenite Operations Setup iz PPM Tools forme." & vbCrLf & _
            "Close this dialog and run Operations Setup from the PPM Tools form.", _
            "PPM - Operations Setup", _
            System.Windows.Forms.MessageBoxButtons.OK, _
            System.Windows.Forms.MessageBoxIcon.Information)
        GoTo Cleanup
    End If
    If dlg.DialogResult <> System.Windows.Forms.DialogResult.OK Then GoTo Cleanup

    ' ── Build selected-ids set ────────────────────────────────────
    Dim selectedIds As New System.Collections.Generic.HashSet(Of String)( _
        System.StringComparer.OrdinalIgnoreCase)
    For Each chk As System.Windows.Forms.CheckBox In checkBoxes
        If chk.Checked Then selectedIds.Add(CStr(chk.Tag))
    Next

    ' ── Write iProperties ─────────────────────────────────────────
    ' Every org operation is written: selected=1, not selected=0.
    ' This guarantees all org op columns appear in the BOM regardless
    ' of which ops are checked on any given part. Loops over
    ' targetDocs -- in single-document mode this is just {oDoc}, same
    ' as the original behavior; in multi-select mode it's every
    ' selected part's document. One document's write failure does not
    ' stop the others (isolated per document, same resilience
    ' philosophy as the Organize macro work).
    Dim nMarked As Integer = 0
    Dim nDocsWritten As Integer = 0
    Dim writeFailures As New System.Collections.Generic.List(Of String)

    For Each dTarget As Inventor.Document In targetDocs
        Try
            Dim oPropSets  As PropertySets = dTarget.PropertySets
            Dim oCustom    As PropertySet
            Try
                oCustom = oPropSets.Item("Inventor User Defined Properties")
            Catch
                oCustom = oPropSets.Add("Inventor User Defined Properties")
            End Try

            Dim nMarkedThisDoc As Integer = 0
            For Each op As String() In orgOps
                Dim propName As String  = "PPM_" & op(0).Replace("-", "_")
                Dim propVal  As Integer = If(selectedIds.Contains(op(0)), 1, 0)
                If propVal = 1 Then nMarkedThisDoc += 1
                Try
                    oCustom.Item(propName).Value = propVal
                Catch
                    Try : oCustom.Add(propVal, propName) : Catch : End Try
                End Try
            Next
            nMarked = nMarkedThisDoc ' same selectedIds for every doc, so this is constant across the loop
            nDocsWritten += 1
        Catch ex As Exception
            Dim dName As String = "(unknown)"
            Try : dName = dTarget.DisplayName : Catch : End Try
            writeFailures.Add(dName & ": " & ex.Message)
        End Try
    Next

    If nDocsWritten = 0 Then
        ShowError("Greška pri pisanju iProperty-ja na sve dokumente:" & vbCrLf & _
                  "Error writing iProperties to all documents:" & vbCrLf & vbCrLf & _
                  String.Join(vbCrLf, writeFailures))
        GoTo Cleanup
    End If

    ' ── Auto-closing confirmation ─────────────────────────────────
    ShowSavedConfirmation(nMarked, nDocsWritten)

Cleanup:
    fUI.Dispose() : fSub.Dispose() : fBold.Dispose()

End Sub

' ════════════════════════════════════════════════════════════════════
' SUBROUTINES
' ════════════════════════════════════════════════════════════════════

Sub ParseOrgOps(content As String, _
                ByRef ops As System.Collections.Generic.List(Of String()))
    ' Parses ppm_operations_config.json operations array.
    ' Produces String() {id, name, category} per entry.
    Dim parts() As String = content.Split( _
        New String() {"""id"""}, StringSplitOptions.RemoveEmptyEntries)
    For i As Integer = 1 To parts.Length - 1
        Dim seg As String = parts(i)
        Dim id  As String = ExtractFirstQuotedValue(seg)
        Dim nm  As String = ExtractJsonField(seg, "name")
        Dim cat As String = ExtractJsonField(seg, "category")
        If id.StartsWith("OP-") AndAlso nm <> "" Then
            ops.Add(New String() {id, nm, cat})
        End If
    Next
End Sub

Function ExtractFirstQuotedValue(s As String) As String
    Dim ci As Integer = s.IndexOf(":")
    If ci < 0 Then Return ""
    Dim q1 As Integer = s.IndexOf("""", ci)
    If q1 < 0 Then Return ""
    Dim q2 As Integer = s.IndexOf("""", q1 + 1)
    If q2 < 0 Then Return ""
    Return s.Substring(q1 + 1, q2 - q1 - 1)
End Function

Function ExtractJsonField(block As String, fieldName As String) As String
    Dim key As String = """" & fieldName & """"
    Dim ki  As Integer = block.IndexOf(key)
    If ki < 0 Then Return ""
    Dim ci  As Integer = block.IndexOf(":", ki + key.Length)
    If ci < 0 Then Return ""
    Dim q1  As Integer = block.IndexOf("""", ci + 1)
    If q1 < 0 Then Return ""
    Dim q2  As Integer = block.IndexOf("""", q1 + 1)
    If q2 < 0 Then Return ""
    Return block.Substring(q1 + 1, q2 - q1 - 1)
End Function

Sub ShowSavedConfirmation(nMarked As Integer, Optional nDocs As Integer = 1)
    ' Auto-closes after 2000 ms; manual OK button as fallback.
    Dim cBg      As System.Drawing.Color = System.Drawing.Color.FromArgb(59, 68, 83)
    Dim cSurface As System.Drawing.Color = System.Drawing.Color.FromArgb(72, 82, 98)
    Dim cAccent  As System.Drawing.Color = System.Drawing.Color.FromArgb(46, 125, 209)
    Dim cText    As System.Drawing.Color = System.Drawing.Color.FromArgb(230, 237, 243)
    Dim cSub     As System.Drawing.Color = System.Drawing.Color.FromArgb(180, 190, 200)
    Dim cGreen   As System.Drawing.Color = System.Drawing.Color.FromArgb(63, 185, 80)

    Dim sf As New System.Windows.Forms.Form
    sf.Text            = "PPM - Operacije sačuvane / Operations Saved"
    sf.Size            = New System.Drawing.Size(380, 170)
    sf.StartPosition   = System.Windows.Forms.FormStartPosition.CenterScreen
    sf.FormBorderStyle = System.Windows.Forms.FormBorderStyle.FixedDialog
    sf.BackColor       = cBg : sf.MaximizeBox = False
    sf.AutoScaleMode   = System.Windows.Forms.AutoScaleMode.None

    Dim lblSaved As New System.Windows.Forms.Label
    lblSaved.Text      = "Operacije sačuvane / Operations saved"
    lblSaved.Font      = New System.Drawing.Font("Segoe UI", 10, System.Drawing.FontStyle.Bold)
    lblSaved.ForeColor = cGreen
    lblSaved.Location  = New System.Drawing.Point(20, 22)
    lblSaved.Size      = New System.Drawing.Size(340, 22)
    sf.Controls.Add(lblSaved)

    Dim lblCount As New System.Windows.Forms.Label
    If nDocs > 1 Then
        lblCount.Text = nMarked & " operacija označeno na " & nDocs & " delova / " & _
                        nMarked & " operations marked on " & nDocs & " parts"
    Else
        lblCount.Text = nMarked & " operacija označeno / " & nMarked & " operations marked"
    End If
    lblCount.Font      = New System.Drawing.Font("Segoe UI", 9)
    lblCount.ForeColor = cSub
    lblCount.Location  = New System.Drawing.Point(20, 48)
    lblCount.Size      = New System.Drawing.Size(340, 18)
    sf.Controls.Add(lblCount)

    Dim sep As New System.Windows.Forms.Label
    sep.BackColor = cSurface
    sep.Location  = New System.Drawing.Point(20, 80)
    sep.Size      = New System.Drawing.Size(340, 1)
    sf.Controls.Add(sep)

    Dim btnOK As New System.Windows.Forms.Button
    btnOK.Text      = "OK"
    btnOK.Font      = New System.Drawing.Font("Segoe UI", 9, System.Drawing.FontStyle.Bold)
    btnOK.BackColor = cAccent : btnOK.ForeColor = cText
    btnOK.FlatStyle = System.Windows.Forms.FlatStyle.Flat
    btnOK.FlatAppearance.BorderColor = cAccent
    btnOK.Location     = New System.Drawing.Point(130, 94)
    btnOK.Size         = New System.Drawing.Size(120, 32)
    btnOK.DialogResult = System.Windows.Forms.DialogResult.OK
    sf.Controls.Add(btnOK)
    sf.AcceptButton = btnOK

    ' System.Windows.Forms.Timer fires on the UI thread during ShowDialog's
    ' message loop — safe to call sf.Close() directly from the tick handler.
    Dim tmr As New System.Windows.Forms.Timer
    tmr.Interval = 2000
    AddHandler tmr.Tick, Sub(s, e)
        tmr.Stop()
        sf.Close()
    End Sub
    tmr.Start()
    sf.ShowDialog()
    tmr.Dispose()
End Sub

Sub ShowError(msg As String)
    Dim ef As New System.Windows.Forms.Form
    ef.Text            = "PPM - Greška / Error"
    ef.Size            = New System.Drawing.Size(460, 200)
    ef.StartPosition   = System.Windows.Forms.FormStartPosition.CenterScreen
    ef.FormBorderStyle = System.Windows.Forms.FormBorderStyle.FixedDialog
    ef.BackColor       = System.Drawing.Color.FromArgb(59, 68, 83) : ef.MaximizeBox = False
    ef.AutoScaleMode   = System.Windows.Forms.AutoScaleMode.None
    Dim lbl As New System.Windows.Forms.Label
    lbl.Text      = msg
    lbl.Font      = New System.Drawing.Font("Segoe UI", 9)
    lbl.ForeColor = System.Drawing.Color.FromArgb(210, 153, 34)
    lbl.Location  = New System.Drawing.Point(20, 20) : lbl.Size = New System.Drawing.Size(420, 80)
    ef.Controls.Add(lbl)
    Dim btn As New System.Windows.Forms.Button
    btn.Text      = "OK"
    btn.Font      = New System.Drawing.Font("Segoe UI", 9, System.Drawing.FontStyle.Bold)
    btn.BackColor = System.Drawing.Color.FromArgb(46, 125, 209)
    btn.ForeColor = System.Drawing.Color.FromArgb(230, 237, 243)
    btn.FlatStyle = System.Windows.Forms.FlatStyle.Flat
    btn.Location  = New System.Drawing.Point(180, 134) : btn.Size = New System.Drawing.Size(100, 32)
    btn.DialogResult = System.Windows.Forms.DialogResult.OK
    ef.Controls.Add(btn) : ef.AcceptButton = btn : ef.ShowDialog()
End Sub
