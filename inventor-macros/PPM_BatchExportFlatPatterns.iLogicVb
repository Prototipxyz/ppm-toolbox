' PPM_BatchExportFlatPatterns.iLogicVb
' Batch assembly-level flat pattern DXF export for Inventor 2021
' Architecture: D-208, D-209, D-210. API patterns: D-251 to D-258.
' Walk strategy: ThisApplication.Documents (crash-safe)
' Qty source: auto-detect BOM xlsx next to assembly, or manual browse, fallback qty=1
' xlsx parsing: ZIP+XML reader (no OLEDB dependency)
' v2 patches:
'   - Mirrored/derived parts (_MIR suffix): detected, skipped, qty merged into source PN
'   - Weldment children (Inseparable sub-asm): collected via sub-asm BOM API, qty = weldment_qty * child_qty
'   - Dialog padding: form widened to 560px, textboxes 400px, buttons repositioned

AddReference "System.Drawing"
AddReference "System.Windows.Forms"
AddReference "System.Xml"
AddReference "System.IO.Compression"
AddReference "System.IO.Compression.FileSystem"

Sub Main()
    ' Main() MUST be parameterless -- confirmed real constraint (D-709,
    ' live compile error on PPM_ExportPartData). Same pattern applied
    ' here: Main reads RuleArguments (if passed via RunExternalRule),
    ' falls through to defaults on normal argument-less invocation, then
    ' calls DoExport which holds all the actual logic.
    Dim jpMode   As Boolean = False
    Dim jpFolder As String = ""
    Try
        If RuleArguments.Exists("JobPackageMode") Then
            jpMode = CBool(RuleArguments("JobPackageMode"))
        End If
        If RuleArguments.Exists("JobPackageDestFolder") Then
            jpFolder = CStr(RuleArguments("JobPackageDestFolder"))
        End If
    Catch
    End Try
    DoExport(jpMode, jpFolder)
End Sub

Sub DoExport(Optional JobPackageMode As Boolean = False, _
        Optional JobPackageDestFolder As String = "")
    ' JobPackageMode / JobPackageDestFolder -- NEW (D-681 step 3). Both
    ' default to the exact original standalone behavior (interactive
    ' destination dialog, per-run summary popup) when called with no
    ' arguments. Intended for the future PPM_SendToEstimator orchestrator:
    ' JobPackageDestFolder, when non-empty, skips the interactive
    ' destination dialog entirely and writes DXFs directly there
    ' (creating the folder if missing) -- this dialog is this project's
    ' own code, not a native Inventor command, so bypassing it directly
    ' is more robust than SendKeys (consistent with D-709's reasoning).
    ' JobPackageMode=True additionally suppresses the per-run ShowSummary
    ' popup, since an orchestrator running multiple steps sequentially
    ' shouldn't be interrupted by intermediate dialogs requiring manual
    ' OK clicks -- DESIGN DECISION, not explicitly in the original spec
    ' (which only covered PPM_ExportPartData's REPORT sheet), but follows
    ' the same "no per-part prompts, no blocking" principle already
    ' established for batch operations (D-209) and the orchestrator's own
    ' "chains all steps sequentially in one click" design (D-325). Result
    ' counts are written back into RuleArguments (if available) so the
    ' orchestrator can build its own consolidated summary instead.
    ' bomFilePath auto-detection and includeBendLines' True default both
    ' already run/apply BEFORE the dialog block below either way, so
    ' Job Package mode gets the same sensible defaults without needing
    ' separate parameters for them.
    ' NOT YET LIVE-TESTED.

    ' ── Auto-update check ────────────────────────────────────────
    Dim localPath   As String = "C:\PPM Cuts and Bends\iLogic\PPM_BatchExportFlatPatterns.iLogicVb"
    Dim networkPath As String = "X:\USER\Gavrilovic\iLogic\PPM_BatchExportFlatPatterns.iLogicVb"
    Try
        If System.IO.File.Exists(networkPath) AndAlso System.IO.File.Exists(localPath) Then
            Dim netTime   As DateTime = System.IO.File.GetLastWriteTime(networkPath)
            Dim localTime As DateTime = System.IO.File.GetLastWriteTime(localPath)
            If netTime > localTime Then
                System.IO.File.Copy(networkPath, localPath, True)
                System.Windows.Forms.MessageBox.Show( _
                    "Nova verzija je instalirana." & vbCrLf & _
                    "New version installed." & vbCrLf & vbCrLf & _
                    "Pokrenite makro ponovo." & vbCrLf & _
                    "Please run the macro again.", _
                    "PPM - Azuriranje / Update", _
                    System.Windows.Forms.MessageBoxButtons.OK, _
                    System.Windows.Forms.MessageBoxIcon.Information)
                Exit Sub
            End If
        End If
    Catch : End Try
    ' ─────────────────────────────────────────────────────────────

    ' ── Palette (D-258) ──────────────────────────────────────────
    Dim cBg      As System.Drawing.Color = System.Drawing.Color.FromArgb(59, 68, 83)
    Dim cSurface As System.Drawing.Color = System.Drawing.Color.FromArgb(72, 82, 98)
    Dim cAccent  As System.Drawing.Color = System.Drawing.Color.FromArgb(46, 125, 209)
    Dim cText    As System.Drawing.Color = System.Drawing.Color.FromArgb(230, 237, 243)
    Dim cSub     As System.Drawing.Color = System.Drawing.Color.FromArgb(180, 190, 200)
    Dim cGreen   As System.Drawing.Color = System.Drawing.Color.FromArgb(63, 185, 80)
    Dim cAmber   As System.Drawing.Color = System.Drawing.Color.FromArgb(210, 153, 34)
    Dim cInput   As System.Drawing.Color = System.Drawing.Color.FromArgb(33, 38, 45)

    Dim fUI   As New System.Drawing.Font("Segoe UI", 9)
    Dim fSub  As New System.Drawing.Font("Segoe UI", 8)
    Dim fBold As New System.Drawing.Font("Segoe UI", 9, System.Drawing.FontStyle.Bold)
    Dim fMono As New System.Drawing.Font("Consolas", 10, System.Drawing.FontStyle.Bold)

    ' ── Guard ────────────────────────────────────────────────────
    If Not TypeOf ThisApplication.ActiveDocument Is AssemblyDocument Then
        ShowError("Otvori sklop (.iam) pre pokretanja makroa." & vbCrLf & _
                  "Open an assembly (.iam) before running this macro.")
        GoTo Cleanup
    End If

    Dim oAsmDoc As AssemblyDocument = CType(ThisApplication.ActiveDocument, AssemblyDocument)
    Dim asmPath As String = oAsmDoc.FullFileName
    Dim asmName As String = System.IO.Path.GetFileNameWithoutExtension(asmPath)
    Dim asmDir  As String = System.IO.Path.GetDirectoryName(asmPath)

    ' ── Auto-export BOM to Excel next to assembly ─────────────────
    ' Uses Inventor BOM API: enables Parts Only view, exports to xlsx.
    ' File saved as AssemblyName_Parts_BOM.xlsx in the assembly folder.
    ' Falls back to auto-detect if export fails.
    Dim autoBomPath  As String = ""
    Dim bomAutoExported As Boolean = False
    Dim bomExportError As String = ""

    Dim expectedBomPath As String = System.IO.Path.Combine(
        asmDir, asmName & "_Parts_BOM.xlsx")

    Try
        Dim oBOM As BOM = oAsmDoc.ComponentDefinition.BOM
        oBOM.PartsOnlyViewEnabled = True
        Dim oView As BOMView = oBOM.BOMViews.Item("Parts Only")
        ' Delete existing file first — Export does not overwrite cleanly on all versions
        If System.IO.File.Exists(expectedBomPath) Then
            System.IO.File.Delete(expectedBomPath)
        End If
        oView.Export(expectedBomPath, kMicrosoftExcelFormat)
        autoBomPath = expectedBomPath
        bomAutoExported = True
    Catch ex As Exception
        bomExportError = ex.Message
        ' Fallback: scan assembly folder for existing BOM xlsx
        Try
            Dim candidates() As String = System.IO.Directory.GetFiles(asmDir, "*.xlsx")
            For Each f As String In candidates
                Dim fn As String = System.IO.Path.GetFileNameWithoutExtension(f).ToLower()
                Dim an As String = asmName.ToLower()
                If fn.StartsWith(an) OrElse fn.Contains(an) OrElse fn.Contains("bom") Then
                    autoBomPath = f
                    Exit For
                End If
            Next
        Catch : End Try
    End Try

    ' ── Build upfront dialog ──────────────────────────────────────
    ' Load last used destination folder from temp file
    Dim lastPathFile As String = System.IO.Path.Combine(
        System.IO.Path.GetTempPath(), "PPM_BatchExport_LastFolder.txt")
    Dim lastFolder As String = ""
    Try
        If System.IO.File.Exists(lastPathFile) Then
            lastFolder = System.IO.File.ReadAllText(lastPathFile).Trim()
        End If
    Catch : End Try

    Dim destFolder  As String  = ""
    Dim bomFilePath As String  = autoBomPath
    Dim includeBendLines As Boolean = True

    If JobPackageDestFolder <> "" Then
        ' ── Job Package mode: skip the interactive dialog entirely ──
        destFolder = JobPackageDestFolder
        Try
            If Not System.IO.Directory.Exists(destFolder) Then
                System.IO.Directory.CreateDirectory(destFolder)
            End If
        Catch ex As Exception
            ShowError("Ne mogu da kreiram odredisni folder:" & vbCrLf & _
                      "Could not create destination folder:" & vbCrLf & vbCrLf & _
                      destFolder & vbCrLf & vbCrLf & ex.Message)
            GoTo Cleanup
        End Try
        ' bomFilePath stays at auto-detected autoBomPath, includeBendLines
        ' stays at its True default -- both already sensible without the
        ' interactive dialog's overrides.
    Else

    Dim dlg As New System.Windows.Forms.Form
    dlg.Text = "PPM - Batch Export Flat Patterns"
    dlg.Size = New System.Drawing.Size(560, 400)
    dlg.StartPosition = System.Windows.Forms.FormStartPosition.CenterScreen
    dlg.FormBorderStyle = System.Windows.Forms.FormBorderStyle.FixedDialog
    dlg.MaximizeBox = False : dlg.MinimizeBox = False
    dlg.BackColor = cBg
    dlg.AutoScaleMode = System.Windows.Forms.AutoScaleMode.None

    Dim lblHeader As New System.Windows.Forms.Label
    lblHeader.Text = "BATCH EXPORT - FLAT PATTERNS"
    lblHeader.Font = New System.Drawing.Font("Segoe UI", 10, System.Drawing.FontStyle.Bold)
    lblHeader.ForeColor = cAccent
    lblHeader.Location = New System.Drawing.Point(20, 18)
    lblHeader.Size = New System.Drawing.Size(520, 22)
    dlg.Controls.Add(lblHeader)

    Dim lblAsm As New System.Windows.Forms.Label
    lblAsm.Text = "Sklop: " & asmName
    lblAsm.Font = fMono
    lblAsm.ForeColor = cGreen
    lblAsm.Location = New System.Drawing.Point(20, 46)
    lblAsm.Size = New System.Drawing.Size(520, 20)
    dlg.Controls.Add(lblAsm)

    ' Separator
    Dim sep1 As New System.Windows.Forms.Label
    sep1.BackColor = cSurface
    sep1.Location = New System.Drawing.Point(20, 74)
    sep1.Size = New System.Drawing.Size(520, 1)
    dlg.Controls.Add(sep1)

    ' Destination folder
    Dim lblFolder As New System.Windows.Forms.Label
    lblFolder.Text = "Odredisni folder / Destination folder:"
    lblFolder.Font = fUI : lblFolder.ForeColor = cSub
    lblFolder.Location = New System.Drawing.Point(20, 86)
    lblFolder.Size = New System.Drawing.Size(300, 18)
    dlg.Controls.Add(lblFolder)

    Dim txtFolder As New System.Windows.Forms.TextBox
    txtFolder.Font = fSub : txtFolder.BackColor = cInput
    txtFolder.ForeColor = cSub : txtFolder.ReadOnly = False
    txtFolder.Text = If(lastFolder <> "", lastFolder, "(nije izabran / not selected)")
    txtFolder.Location = New System.Drawing.Point(20, 108)
    txtFolder.Size = New System.Drawing.Size(376, 22)
    dlg.Controls.Add(txtFolder)

    Dim btnBrowseFolder As New System.Windows.Forms.Button
    btnBrowseFolder.Text = "..." : btnBrowseFolder.Font = fBold
    btnBrowseFolder.BackColor = cSurface : btnBrowseFolder.ForeColor = cText
    btnBrowseFolder.FlatStyle = System.Windows.Forms.FlatStyle.Flat
    btnBrowseFolder.FlatAppearance.BorderColor = cAccent
    btnBrowseFolder.Location = New System.Drawing.Point(404, 107)
    btnBrowseFolder.Size = New System.Drawing.Size(116, 24)
    dlg.Controls.Add(btnBrowseFolder)

    ' Separator
    Dim sep2 As New System.Windows.Forms.Label
    sep2.BackColor = cSurface
    sep2.Location = New System.Drawing.Point(20, 142)
    sep2.Size = New System.Drawing.Size(520, 1)
    dlg.Controls.Add(sep2)

    ' BOM file row
    Dim lblBom As New System.Windows.Forms.Label
    lblBom.Font = fSub : lblBom.ForeColor = cSub
    lblBom.Location = New System.Drawing.Point(20, 152)
    lblBom.Size = New System.Drawing.Size(520, 18)
    dlg.Controls.Add(lblBom)

    Dim txtBom As New System.Windows.Forms.TextBox
    txtBom.Font = fSub : txtBom.BackColor = cInput
    txtBom.ReadOnly = True
    txtBom.Location = New System.Drawing.Point(20, 174)
    txtBom.Size = New System.Drawing.Size(376, 22)
    dlg.Controls.Add(txtBom)

    ' Set BOM field initial state
    If bomAutoExported Then
        lblBom.Text = "BOM Excel (auto-izvezen / auto-exported):"
        txtBom.Text = System.IO.Path.GetFileName(autoBomPath)
        txtBom.ForeColor = cGreen
    ElseIf autoBomPath <> "" Then
        lblBom.Text = "BOM Excel (BOM export nije uspio, koristi postojeci / export failed, using existing):"
        txtBom.Text = System.IO.Path.GetFileName(autoBomPath)
        txtBom.ForeColor = cAmber
    Else
        lblBom.Text = "BOM Excel (export nije uspio / export failed - kolicine=1):"
        txtBom.Text = If(bomExportError <> "", bomExportError, "(nije pronadjen / not found)")
        txtBom.ForeColor = System.Drawing.Color.FromArgb(210, 100, 100)
    End If

    Dim btnBrowseBom As New System.Windows.Forms.Button
    btnBrowseBom.Text = "..." : btnBrowseBom.Font = fBold
    btnBrowseBom.BackColor = cSurface : btnBrowseBom.ForeColor = cText
    btnBrowseBom.FlatStyle = System.Windows.Forms.FlatStyle.Flat
    btnBrowseBom.FlatAppearance.BorderColor = cAccent
    btnBrowseBom.Location = New System.Drawing.Point(404, 173)
    btnBrowseBom.Size = New System.Drawing.Size(116, 24)
    dlg.Controls.Add(btnBrowseBom)

    Dim lblBomHint As New System.Windows.Forms.Label
    lblBomHint.Text = "BOM se automatski izvozi u folder sklopa. Koristite '...' za rucni odabir drugog fajla."
    lblBomHint.Font = New System.Drawing.Font("Segoe UI", 7)
    lblBomHint.ForeColor = System.Drawing.Color.FromArgb(120, 140, 160)
    lblBomHint.Location = New System.Drawing.Point(20, 200)
    lblBomHint.Size = New System.Drawing.Size(520, 16)
    dlg.Controls.Add(lblBomHint)

    ' Separator
    Dim sep3 As New System.Windows.Forms.Label
    sep3.BackColor = cSurface
    sep3.Location = New System.Drawing.Point(20, 224)
    sep3.Size = New System.Drawing.Size(520, 1)
    dlg.Controls.Add(sep3)

    ' Bend lines checkbox
    Dim chkBend As New System.Windows.Forms.CheckBox
    chkBend.Text = "Ukljuci linije savijanja / Include bend lines (IV_BEND, IV_BEND_DOWN)"
    chkBend.Font = fUI : chkBend.ForeColor = cText : chkBend.BackColor = cBg
    chkBend.Checked = False
    chkBend.Location = New System.Drawing.Point(20, 234)
    chkBend.Size = New System.Drawing.Size(520, 22)
    dlg.Controls.Add(chkBend)

    Dim lblNote As New System.Windows.Forms.Label
    lblNote.Text = "Preskocice ne-lim delove. Duplikati se izvoze jednom. Delovi u ogledalu (_MIR) se spajaju sa originalnim." & vbCrLf & _
                   "Non-SM parts skipped. Duplicates exported once. Mirrored parts (_MIR) qty merged into source."
    lblNote.Font = fSub : lblNote.ForeColor = cSub
    lblNote.Location = New System.Drawing.Point(20, 262)
    lblNote.Size = New System.Drawing.Size(520, 30)
    dlg.Controls.Add(lblNote)

    ' Separator + buttons
    Dim sep4 As New System.Windows.Forms.Label
    sep4.BackColor = cSurface
    sep4.Location = New System.Drawing.Point(20, 300)
    sep4.Size = New System.Drawing.Size(520, 1)
    dlg.Controls.Add(sep4)

    Dim btnCancel As New System.Windows.Forms.Button
    btnCancel.Text = "Otkazi / Cancel" : btnCancel.Font = fUI
    btnCancel.BackColor = cSurface : btnCancel.ForeColor = cSub
    btnCancel.FlatStyle = System.Windows.Forms.FlatStyle.Flat
    btnCancel.FlatAppearance.BorderColor = cSurface
    btnCancel.Location = New System.Drawing.Point(90, 320)
    btnCancel.Size = New System.Drawing.Size(160, 34)
    btnCancel.DialogResult = System.Windows.Forms.DialogResult.Cancel
    dlg.Controls.Add(btnCancel)

    Dim btnExport As New System.Windows.Forms.Button
    btnExport.Text = "Pokreni Export / Start Export" : btnExport.Font = fBold
    btnExport.BackColor = cAccent : btnExport.ForeColor = cText
    btnExport.FlatStyle = System.Windows.Forms.FlatStyle.Flat
    btnExport.FlatAppearance.BorderColor = cAccent
    btnExport.Location = New System.Drawing.Point(290, 320)
    btnExport.Size = New System.Drawing.Size(160, 34)
    btnExport.DialogResult = System.Windows.Forms.DialogResult.OK
    btnExport.Enabled = False
    dlg.Controls.Add(btnExport)

    dlg.AcceptButton = btnExport
    dlg.CancelButton = btnCancel

    ' Pre-enable export button if last folder is valid
    If lastFolder <> "" AndAlso System.IO.Directory.Exists(lastFolder) Then
        destFolder = lastFolder
        txtFolder.ForeColor = cGreen
        btnExport.Enabled = True
    End If

    AddHandler btnBrowseFolder.Click, Sub(s, e)
        Dim fbd As New System.Windows.Forms.FolderBrowserDialog
        fbd.Description = "Izaberi odredisni folder / Select destination folder"
        ' Open at last used location or at typed path if valid
        Dim typedPath As String = txtFolder.Text.Trim()
        If System.IO.Directory.Exists(typedPath) Then
            fbd.SelectedPath = typedPath
        ElseIf lastFolder <> "" AndAlso System.IO.Directory.Exists(lastFolder) Then
            fbd.SelectedPath = lastFolder
        End If
        If fbd.ShowDialog() = System.Windows.Forms.DialogResult.OK Then
            destFolder = fbd.SelectedPath
            txtFolder.Text = destFolder
            txtFolder.ForeColor = cGreen
            btnExport.Enabled = True
        End If
    End Sub

    ' Also enable export when user types/pastes a valid path directly
    AddHandler txtFolder.TextChanged, Sub(s, e)
        Dim typed As String = txtFolder.Text.Trim()
        If System.IO.Directory.Exists(typed) Then
            destFolder = typed
            txtFolder.ForeColor = cGreen
            btnExport.Enabled = True
        Else
            btnExport.Enabled = False
        End If
    End Sub

    AddHandler btnBrowseBom.Click, Sub(s, e)
        Dim ofd As New System.Windows.Forms.OpenFileDialog
        ofd.Title = "Izaberi BOM Excel / Select BOM Excel"
        ofd.Filter = "Excel files (*.xlsx)|*.xlsx|All files (*.*)|*.*"
        ofd.InitialDirectory = If(System.IO.Directory.Exists(asmDir), asmDir, "")
        If ofd.ShowDialog() = System.Windows.Forms.DialogResult.OK Then
            bomFilePath = ofd.FileName
            txtBom.Text = System.IO.Path.GetFileName(bomFilePath)
            txtBom.ForeColor = cGreen
            lblBom.Text = "BOM Excel (rucno izabran / manually selected):"
        End If
    End Sub

    If dlg.ShowDialog() <> System.Windows.Forms.DialogResult.OK Then GoTo Cleanup

    ' Read destFolder from text box in case user typed/pasted it
    destFolder = txtFolder.Text.Trim()
    If Not System.IO.Directory.Exists(destFolder) Then
        ShowError("Odredisni folder ne postoji." & vbCrLf & "Destination folder does not exist.")
        GoTo Cleanup
    End If

    ' Save last used folder for next run
    Try : System.IO.File.WriteAllText(lastPathFile, destFolder) : Catch : End Try

    includeBendLines = chkBend.Checked
    End If

    ' ── Load BOM qty from xlsx ────────────────────────────────────
    Dim qtyMap   As New System.Collections.Generic.Dictionary(Of String, Integer)
    Dim bomLoaded As Boolean = False

    If bomFilePath <> "" AndAlso System.IO.File.Exists(bomFilePath) Then
        Try
            ReadBomXlsx(bomFilePath, qtyMap)
            bomLoaded = (qtyMap.Count > 0)
        Catch
            bomLoaded = False
        End Try
    End If

    ' ── Collect sheet metal parts referenced by this assembly ────────
    ' Build set of file paths belonging to this assembly using
    ' ReferencedDocuments — safer than AllReferencedFiles in iLogic context.
    Dim partMap As New System.Collections.Generic.Dictionary(Of String, Object())

    Dim asmRefPaths As New System.Collections.Generic.HashSet(Of String)(
        System.StringComparer.OrdinalIgnoreCase)
    Try
        CollectReferencedPaths(oAsmDoc, asmRefPaths)
    Catch : End Try

    ' Always include the assembly file itself as a sanity reference
    Try : asmRefPaths.Add(oAsmDoc.FullFileName) : Catch : End Try

    ' ── Build qty override map: merge _MIR qty into source PN ────────────────
    ' For each PN ending in _MIR: find source PN (strip _MIR suffix),
    ' add MIR qty to source qty in qtyMap so the source DXF gets combined qty.
    ' MIR parts themselves are never exported (no flat pattern on derived parts).
    Dim mirMergeLog As New System.Collections.Generic.List(Of String)
    If bomLoaded Then
        Dim mirKeys As New System.Collections.Generic.List(Of String)
        For Each k As String In qtyMap.Keys
            If k.EndsWith("_MIR") Then mirKeys.Add(k)
        Next
        For Each mirKey As String In mirKeys
            Dim sourceKey As String = mirKey.Substring(0, mirKey.Length - 4).ToUpper() ' strip _MIR
            Dim mirQty As Integer = qtyMap(mirKey)
            If qtyMap.ContainsKey(sourceKey) Then
                qtyMap(sourceKey) += mirQty
                mirMergeLog.Add(mirKey & " (" & mirQty & ") → spojen sa / merged into " & sourceKey)
            Else
                ' Source PN not in BOM — keep MIR entry so it gets exported standalone
                ' (edge case: only the MIR variant exists, not the original)
                mirMergeLog.Add(mirKey & " (" & mirQty & ") — original nije u BOM / not in BOM, izvozi se odvojeno / exported standalone")
            End If
        Next
    End If

    ' ── Collect weldment (Inseparable) sub-assembly children ─────────────────
    ' Top-level Parts Only BOM suppresses children of Inseparable sub-assemblies.
    ' For each Inseparable sub-asm: call its own BOM API to get child PNs + qtys,
    ' multiply by weldment qty in top BOM, inject into qtyMap.
    ' Falls back to qty=1 per child if sub-asm BOM API fails.
    Dim weldmentLog As New System.Collections.Generic.List(Of String)
    CollectWeldmentChildren(oAsmDoc, qtyMap, bomLoaded, weldmentLog)

    For Each oDoc As Document In ThisApplication.Documents
        If Not TypeOf oDoc Is PartDocument Then Continue For

        Dim docPath As String = ""
        Try : docPath = oDoc.FullFileName : Catch : Continue For : End Try

        ' Skip if not referenced by this assembly
        ' If reference collection failed entirely (empty), skip all — safer than no filter
        If Not asmRefPaths.Contains(docPath) Then Continue For

        Dim oPart As PartDocument = Nothing
        Try : oPart = CType(oDoc, PartDocument) : Catch : Continue For : End Try
        Try
            If Not TypeOf oPart.ComponentDefinition Is SheetMetalComponentDefinition Then
                Continue For
            End If
        Catch : Continue For : End Try

        ' ── Skip mirrored/derived parts — they have no flat pattern ──────────
        ' DerivedPartComponentDefinition type not available in iLogic 2021 sandbox.
        ' Detect by _MIR filename suffix (confirmed naming convention).
        Dim fnCheck As String = System.IO.Path.GetFileNameWithoutExtension(docPath).ToUpper()
        If fnCheck.EndsWith("_MIR") Then Continue For  ' qty already merged into source above

        Dim pn As String = ""
        Try
            Dim oProp As Inventor.Property = _
                oPart.PropertySets.Item("Design Tracking Properties").Item("Part Number")
            pn = CStr(oProp.Value).Trim()
        Catch : End Try
        If pn = "" Then
            Try : pn = System.IO.Path.GetFileNameWithoutExtension(oPart.FullFileName)
            Catch : pn = "UNKNOWN_" & partMap.Count.ToString() : End Try
        End If

        Dim qty As Integer = 1
        If bomLoaded AndAlso qtyMap.ContainsKey(pn.ToUpper()) Then
            qty = qtyMap(pn.ToUpper())
        End If

        If Not partMap.ContainsKey(docPath.ToLower()) Then
            partMap(docPath.ToLower()) = New Object() {oPart, qty, pn}
        End If
    Next

    If partMap.Count = 0 Then
        ShowError("Nisu pronadjeni lim delovi." & vbCrLf & _
                  "No sheet metal parts found in loaded documents.")
        GoTo Cleanup
    End If

    ' ── Export loop ───────────────────────────────────────────────
    Dim nExported As Integer = 0
    Dim nSkipped  As Integer = 0
    Dim nFailed   As Integer = 0
    Dim nQty1     As Integer = 0
    Dim failList    As New System.Collections.Generic.List(Of String)
    Dim missingBom  As New System.Collections.Generic.List(Of String)

    For Each kvp In partMap
        Dim entry()  As Object = kvp.Value
        Dim oPartDoc As PartDocument = CType(entry(0), PartDocument)
        Dim qty      As Integer = CInt(entry(1))
        Dim pn       As String = CStr(entry(2))

        If bomLoaded AndAlso qty = 1 AndAlso Not qtyMap.ContainsKey(pn.ToUpper()) Then
            nQty1 += 1
            missingBom.Add(pn)
        End If

        Try
            Dim oSMDef As SheetMetalComponentDefinition = _
                CType(oPartDoc.ComponentDefinition, SheetMetalComponentDefinition)

            Dim material As String = "UNKNOWN"
            Try
                material = oPartDoc.ComponentDefinition.Material.Name
                material = SanitizeForFilename(material)
            Catch : End Try

            Dim thickMM As Double = 0
            Try : thickMM = oSMDef.Thickness.ModelValue * 10 : Catch : End Try
            Dim thickStr As String = FormatThickness(thickMM)

            Dim filename As String = pn & "_" & material & "_" & thickStr & "mm_" & qty & "pcs.dxf"
            ' Sort into subfolders: DestFolder\MATERIAL\THICKNESSmm\filename
            Dim subFolder As String = System.IO.Path.Combine(destFolder, material, thickStr & "mm")
            Try
                If Not System.IO.Directory.Exists(subFolder) Then
                    System.IO.Directory.CreateDirectory(subFolder)
                End If
            Catch : End Try
            Dim destPath As String = System.IO.Path.Combine(subFolder, filename)

            ' D-210: skip if DXF newer than part
            If System.IO.File.Exists(destPath) Then
                Dim dxfTime  As DateTime = System.IO.File.GetLastWriteTime(destPath)
                Dim partTime As DateTime = System.IO.File.GetLastWriteTime(oPartDoc.FullFileName)
                If partTime <= dxfTime Then
                    nSkipped += 1
                    Continue For
                End If
            End If

            ' Activate the part and wait until Inventor confirms it is the active document.
            ' Fixed sleep is unreliable — poll instead with a 5-second timeout.
            Try
                oPartDoc.Activate()
                Dim waited As Integer = 0
                Do While waited < 5000
                    Try
                        If ThisApplication.ActiveDocument Is oPartDoc Then Exit Do
                    Catch : End Try
                    System.Threading.Thread.Sleep(100)
                    waited += 100
                Loop
            Catch : End Try

            Try
                ' Export flat pattern DXF (D-251)
                Dim oDataIO As DataIO = oPartDoc.ComponentDefinition.DataIO
                Dim iniPath As String = If(includeBendLines, _
                    "C:\PPM Cuts and Bends\iLogic\PPM_FlatPattern_WithBends.ini", _
                    "C:\PPM Cuts and Bends\iLogic\PPM_FlatPattern_NoBends.ini")
                oDataIO.WriteDataToFile("FLAT PATTERN DXF?Configuration=" & iniPath, destPath)

                FilterDxfLayers(destPath, includeBendLines)

                ' XDATA removed — broke AutoCAD compatibility; info in filename

                nExported += 1

            Catch ex As Exception
                nFailed += 1
                failList.Add(pn & " - " & ex.Message)

            Finally
                ' Reactivate the assembly — returns Inventor to assembly context
                ' and implicitly exits any flat pattern view on the part
                Try : oAsmDoc.Activate() : Catch : End Try
            End Try

        Catch ex As Exception
            nFailed += 1
            failList.Add(pn & " - " & ex.Message)
        End Try
    Next

    If JobPackageMode Then
        ' No popup in Job Package mode -- see design note in DoExport's
        ' header comment. Writing results back into RuleArguments for
        ' the orchestrator to read was ATTEMPTED and CONFIRMED NOT
        ' POSSIBLE: RuleArguments inside a called rule is typed
        ' Autodesk.iLogic.Interfaces.IRuleArguments, a read-only
        ' interface (confirmed via two real compile errors: indexer
        ' assignment "Property 'Value' is ReadOnly", then ".Add" is not
        ' a member of IRuleArguments either). Simpler working
        ' alternative for the orchestrator instead of a return-value
        ' handoff: count files in JobPackageDestFolder directly after
        ' calling this rule via RunExternalRule.
    Else
        ShowSummary(nExported, nSkipped, nFailed, nQty1, bomLoaded, failList, missingBom, destFolder, mirMergeLog, weldmentLog)
    End If

Cleanup:
    fUI.Dispose() : fSub.Dispose() : fBold.Dispose() : fMono.Dispose()

End Sub

' ════════════════════════════════════════════════════════════════════
' SUBROUTINES
' ════════════════════════════════════════════════════════════════════

Sub CollectReferencedPaths(oDoc As Document, _
                           ByRef paths As System.Collections.Generic.HashSet(Of String))
    ' Recursively collect all file paths referenced by oDoc.
    ' Uses ReferencedDocuments which is safe and available in iLogic 2021.
    '
    ' NEW (OQ-205 / D-703): before recursing into a child ASSEMBLY, check
    ' its own PPM_SubassemblyTreatment iProperty. If "PurchasedUnit", the
    ' assembly's own path is still added (it appears as a single costed
    ' line item, per explicit confirmation) but its CHILDREN are not
    ' recursed into -- their paths never enter the set, so they never
    ' reach the DXF export loop below. Parts are unaffected (only
    ' assemblies can carry this flag/have children to exclude).
    For Each refDoc As Document In oDoc.ReferencedDocuments
        Dim refPath As String = ""
        Try : refPath = refDoc.FullFileName : Catch : Continue For : End Try
        If refPath = "" Then Continue For
        If paths.Contains(refPath) Then Continue For  ' avoid infinite loops on circular refs
        paths.Add(refPath)
        ' Recurse into sub-assemblies -- unless flagged PurchasedUnit
        If TypeOf refDoc Is AssemblyDocument Then
            Dim isPurchased As Boolean = False
            Try
                Dim propVal = refDoc.PropertySets.Item("Inventor User Defined Properties") _
                    .Item("PPM_SubassemblyTreatment").Value.ToString()
                isPurchased = (propVal = "PurchasedUnit")
            Catch
            End Try
            If Not isPurchased Then
                CollectReferencedPaths(refDoc, paths)
            End If
        End If
    Next
End Sub

Sub CollectWeldmentChildren( _
        oTopAsm As AssemblyDocument, _
        ByRef qtyMap As System.Collections.Generic.Dictionary(Of String, Integer), _
        bomLoaded As Boolean, _
        ByRef weldmentLog As System.Collections.Generic.List(Of String))
    ' Finds Inseparable sub-assemblies (weldments) in the top assembly.
    ' For each: reads the weldment's own BOM via API to get child PNs + qtys.
    ' Multiplies by weldment qty in top BOM, injects into qtyMap.
    ' Fallback: qty=1 per child if sub-asm BOM API fails.
    '
    ' Strategy: walk ReferencedDocuments of top asm, find AssemblyDocuments
    ' whose BOMStructure = kInseparableBOMStructure (value 67109120).
    ' kInseparableBOMStructure is an Inventor enum — used as integer literal
    ' to avoid compile errors in iLogic 2021 if enum not in scope.
    Const kInseparable As Integer = 67109120

    For Each refDoc As Document In oTopAsm.ReferencedDocuments
        If Not TypeOf refDoc Is AssemblyDocument Then Continue For
        Dim subAsm As AssemblyDocument = CType(refDoc, AssemblyDocument)

        ' Check if this sub-assembly is Inseparable in the top-level BOM
        Dim isInseparable As Boolean = False
        Try
            ' BOMStructure is a property of the ComponentDefinition
            Dim bsVal As Integer = CInt(subAsm.ComponentDefinition.BOMStructure)
            If bsVal = kInseparable Then isInseparable = True
        Catch : End Try
        If Not isInseparable Then Continue For

        ' Get weldment qty from top BOM (how many times this sub-asm appears)
        Dim weldPN As String = ""
        Try
            Dim wProp As Inventor.Property = _
                subAsm.PropertySets.Item("Design Tracking Properties").Item("Part Number")
            weldPN = CStr(wProp.Value).Trim()
        Catch : End Try
        If weldPN = "" Then
            Try : weldPN = System.IO.Path.GetFileNameWithoutExtension(subAsm.FullFileName)
            Catch : weldPN = "WELD_UNKNOWN" : End Try
        End If

        Dim weldQty As Integer = 1
        If bomLoaded AndAlso qtyMap.ContainsKey(weldPN.ToUpper()) Then
            weldQty = qtyMap(weldPN.ToUpper())
        End If

        ' Read weldment's own BOM to get its children
        Dim childQtyMap As New System.Collections.Generic.Dictionary(Of String, Integer)
        Dim childBomOk As Boolean = False
        Try
            Dim wBOM As BOM = subAsm.ComponentDefinition.BOM
            wBOM.PartsOnlyViewEnabled = True
            Dim wView As BOMView = wBOM.BOMViews.Item("Parts Only")
            ' Export to temp xlsx and parse
            Dim tmpBom As String = System.IO.Path.Combine( _
                System.IO.Path.GetTempPath(), "PPM_WeldBOM_" & weldPN & ".xlsx")
            If System.IO.File.Exists(tmpBom) Then System.IO.File.Delete(tmpBom)
            wView.Export(tmpBom, kMicrosoftExcelFormat)
            If System.IO.File.Exists(tmpBom) Then
                ReadBomXlsx(tmpBom, childQtyMap)
                Try : System.IO.File.Delete(tmpBom) : Catch : End Try
                childBomOk = (childQtyMap.Count > 0)
            End If
        Catch : End Try

        If childBomOk Then
            ' Inject child qtys × weldment qty into main qtyMap
            For Each kvp In childQtyMap
                Dim childPN As String = kvp.Key.ToUpper()
                Dim childQty As Integer = kvp.Value * weldQty
                If qtyMap.ContainsKey(childPN) Then
                    ' Already in top BOM somehow — take the higher value (conservative)
                    qtyMap(childPN) = Math.Max(qtyMap(childPN), childQty)
                Else
                    qtyMap(childPN) = childQty
                End If
            Next
            weldmentLog.Add(weldPN & " (x" & weldQty & "): " & childQtyMap.Count & " dela ucitano iz BOM-a / children loaded from BOM")
        Else
            ' Fallback: walk ReferencedDocuments of sub-asm, assign qty = weldQty per child
            Dim fallbackCount As Integer = 0
            For Each childDoc As Document In subAsm.ReferencedDocuments
                If Not TypeOf childDoc Is PartDocument Then Continue For
                Dim childPart As PartDocument = CType(childDoc, PartDocument)
                Try
                    If Not TypeOf childPart.ComponentDefinition Is SheetMetalComponentDefinition Then
                        Continue For
                    End If
                Catch : Continue For : End Try
                Dim childPN As String = ""
                Try
                    Dim cProp As Inventor.Property = _
                        childPart.PropertySets.Item("Design Tracking Properties").Item("Part Number")
                    childPN = CStr(cProp.Value).Trim().ToUpper()
                Catch : End Try
                If childPN = "" Then
                    Try : childPN = System.IO.Path.GetFileNameWithoutExtension(childDoc.FullFileName).ToUpper()
                    Catch : Continue For : End Try
                End If
                If Not qtyMap.ContainsKey(childPN) Then
                    qtyMap(childPN) = weldQty  ' 1 per weldment occurrence, fallback
                    fallbackCount += 1
                End If
            Next
            weldmentLog.Add(weldPN & " (x" & weldQty & "): BOM API nije uspio / failed — " & _
                            fallbackCount & " dece kolicina=weldQty (amber)")
        End If
    Next
End Sub

Sub ReadBomXlsx(filePath As String, _
                ByRef qtyMap As System.Collections.Generic.Dictionary(Of String, Integer))
    ' Reads Inventor BOM xlsx export without OLEDB.
    ' Parses the xlsx ZIP directly: reads xl/worksheets/sheet1.xml
    ' and xl/sharedStrings.xml to resolve string cells.
    ' Expects headers in row 1: "Part Number" and "QTY" (D-247 confirmed column names).

    ' Copy to temp so we can open as ZipArchive without locking the original
    Dim tmpPath As String = System.IO.Path.GetTempFileName() & ".xlsx"
    System.IO.File.Copy(filePath, tmpPath, True)

    Try
        Using archive As System.IO.Compression.ZipArchive = _
            System.IO.Compression.ZipFile.OpenRead(tmpPath)

            ' ── Load shared strings ───────────────────────────────
            Dim sharedStrings As New System.Collections.Generic.List(Of String)
            Dim ssEntry As System.IO.Compression.ZipArchiveEntry = _
                archive.GetEntry("xl/sharedStrings.xml")
            If ssEntry IsNot Nothing Then
                Using stream As System.IO.Stream = ssEntry.Open()
                    Dim xml As New System.Xml.XmlDocument
                    xml.Load(stream)
                    Dim mgr As New System.Xml.XmlNamespaceManager(xml.NameTable)
                    mgr.AddNamespace("x", "http://schemas.openxmlformats.org/spreadsheetml/2006/main")
                    For Each si As System.Xml.XmlNode In xml.SelectNodes("//x:si", mgr)
                        sharedStrings.Add(si.InnerText)
                    Next
                End Using
            End If

            ' ── Find the BOM sheet ────────────────────────────────
            ' Try sheet1 first, then check workbook.xml for "BOM" sheet index
            Dim sheetPath As String = "xl/worksheets/sheet1.xml"
            Dim wbEntry As System.IO.Compression.ZipArchiveEntry = _
                archive.GetEntry("xl/workbook.xml")
            If wbEntry IsNot Nothing Then
                Using stream As System.IO.Stream = wbEntry.Open()
                    Dim xml As New System.Xml.XmlDocument
                    xml.Load(stream)
                    Dim mgr As New System.Xml.XmlNamespaceManager(xml.NameTable)
                    mgr.AddNamespace("x", "http://schemas.openxmlformats.org/spreadsheetml/2006/main")
                    Dim sheets As System.Xml.XmlNodeList = xml.SelectNodes("//x:sheet", mgr)
                    Dim idx As Integer = 1
                    For Each sh As System.Xml.XmlNode In sheets
                        Dim sName As String = sh.Attributes("name").Value
                        If sName.ToLower() = "bom" Then
                            sheetPath = "xl/worksheets/sheet" & idx & ".xml"
                            Exit For
                        End If
                        idx += 1
                    Next
                End Using
            End If

            ' ── Parse sheet ───────────────────────────────────────
            Dim sheetEntry As System.IO.Compression.ZipArchiveEntry = archive.GetEntry(sheetPath)
            If sheetEntry Is Nothing Then Return

            Using stream As System.IO.Stream = sheetEntry.Open()
                Dim xml As New System.Xml.XmlDocument
                xml.Load(stream)
                Dim mgr As New System.Xml.XmlNamespaceManager(xml.NameTable)
                mgr.AddNamespace("x", "http://schemas.openxmlformats.org/spreadsheetml/2006/main")

                Dim rows As System.Xml.XmlNodeList = xml.SelectNodes("//x:row", mgr)
                Dim pnCol As String = ""   ' e.g. "B"
                Dim qtyCol As String = ""  ' e.g. "F"

                For Each row As System.Xml.XmlNode In rows
                    Dim rowNum As Integer = CInt(row.Attributes("r").Value)
                    Dim cells As System.Xml.XmlNodeList = row.SelectNodes("x:c", mgr)

                    If rowNum = 1 Then
                        ' Header row — find Part Number and QTY columns
                        For Each cell As System.Xml.XmlNode In cells
                            Dim cellRef As String = cell.Attributes("r").Value  ' e.g. "B1"
                            Dim col As String = System.Text.RegularExpressions.Regex.Match(cellRef, "[A-Z]+").Value
                            Dim val As String = GetCellValue(cell, sharedStrings)
                            If val.ToLower() = "part number" Then pnCol = col
                            If val.ToLower() = "qty" Then qtyCol = col
                        Next
                        ' Also accept "unit qty" as fallback for qty (D-247)
                        If qtyCol = "" Then
                            For Each cell As System.Xml.XmlNode In cells
                                Dim cellRef As String = cell.Attributes("r").Value
                                Dim col As String = System.Text.RegularExpressions.Regex.Match(cellRef, "[A-Z]+").Value
                                Dim val As String = GetCellValue(cell, sharedStrings)
                                If val.ToLower() = "unit qty" Then qtyCol = col
                            Next
                        End If
                        Continue For
                    End If

                    If pnCol = "" OrElse qtyCol = "" Then Continue For

                    ' Data rows
                    Dim pnVal  As String = ""
                    Dim qtyVal As Integer = 1

                    For Each cell As System.Xml.XmlNode In cells
                        Dim cellRef As String = cell.Attributes("r").Value
                        Dim col As String = System.Text.RegularExpressions.Regex.Match(cellRef, "[A-Z]+").Value
                        If col = pnCol Then
                            pnVal = GetCellValue(cell, sharedStrings).Trim()
                        ElseIf col = qtyCol Then
                            Try : qtyVal = CInt(GetCellValue(cell, sharedStrings)) : Catch : End Try
                        End If
                    Next

                    If pnVal <> "" Then
                        qtyMap(pnVal.ToUpper()) = qtyVal
                    End If
                Next
            End Using
        End Using
    Finally
        Try : System.IO.File.Delete(tmpPath) : Catch : End Try
    End Try
End Sub

Function GetCellValue(cell As System.Xml.XmlNode, _
                       sharedStrings As System.Collections.Generic.List(Of String)) As String
    Dim mgr As New System.Xml.XmlNamespaceManager(cell.OwnerDocument.NameTable)
    mgr.AddNamespace("x", "http://schemas.openxmlformats.org/spreadsheetml/2006/main")
    Dim vNode As System.Xml.XmlNode = cell.SelectSingleNode("x:v", mgr)
    If vNode Is Nothing Then Return ""
    Dim t As System.Xml.XmlAttribute = cell.Attributes("t")
    If t IsNot Nothing AndAlso t.Value = "s" Then
        ' Shared string index
        Dim idx As Integer = CInt(vNode.InnerText)
        If idx >= 0 AndAlso idx < sharedStrings.Count Then
            Return sharedStrings(idx)
        End If
        Return ""
    End If
    Return vNode.InnerText
End Function

Sub WriteXDATA(filePath As String, material As String, thickStr As String)
    Dim lines As New System.Collections.Generic.List(Of String)(
        System.IO.File.ReadAllLines(filePath))
    Dim eofIdx As Integer = lines.Count - 1
    For idx As Integer = lines.Count - 1 To 0 Step -1
        If lines(idx).Trim() = "EOF" Then : eofIdx = idx : Exit For : End If
    Next
    Dim xdata As New System.Collections.Generic.List(Of String)
    xdata.Add("  0") : xdata.Add("XRECORD")
    xdata.Add("  2") : xdata.Add("PPM_ESTIMATOR")
    xdata.Add("  1") : xdata.Add("MATERIAL=" & material)
    xdata.Add("  1") : xdata.Add("THICKNESS_MM=" & thickStr)
    lines.InsertRange(eofIdx, xdata)
    System.IO.File.WriteAllLines(filePath, lines.ToArray())
End Sub

Sub FilterDxfLayers(filePath As String, includeBendLines As Boolean)
    ' Entity-block whitelist -- ENTITIES section only; all other sections pass through unchanged.
    ' NEVER touches TABLES/LAYER section or group-code 70 layer counts -- editing those in a
    ' prior version broke AutoCAD and laser-software file compatibility.
    '
    ' Reads the DXF in group-code/value pairs (alternating lines) so a data value of "0"
    ' is never confused with the group-code-0 entity delimiter.
    '
    ' Per entity block whitelist:
    '   IV_OUTER_PROFILE, IV_INTERIOR_PROFILES  -> rewrite group code 8 value to "0", keep
    '   0 (explicit or omitted -- DXF default)  -> keep as-is
    '   IV_BEND, IV_BEND_DOWN                   -> keep only if includeBendLines=True
    '   anything else (incl. unrecognised IV_*) -> drop (permissive-drop, not an enumerated blacklist)
    '
    ' POLYLINE note: VERTEX/SEQEND sub-blocks carry their own group-code-8 layer matching the
    ' parent POLYLINE, so this whitelist handles them correctly in isolation (same layer = same
    ' keep/drop decision). Inventor flat-pattern exports are expected to emit only
    ' LINE/ARC/CIRCLE/POINT/LWPOLYLINE -- POLYLINE/VERTEX/SEQEND should not appear in practice.

    Dim lines() As String = System.IO.File.ReadAllLines(filePath)
    Dim out As New System.Collections.Generic.List(Of String)
    Dim i As Integer = 0
    Dim foundEntities As Boolean = False

    ' ── Pass through everything before ENTITIES section ───────────
    Do While i < lines.Length
        If i + 3 < lines.Length AndAlso _
           lines(i).Trim() = "0" AndAlso lines(i + 1).Trim() = "SECTION" AndAlso _
           lines(i + 2).Trim() = "2" AndAlso lines(i + 3).Trim().ToUpper() = "ENTITIES" Then
            out.Add(lines(i)) : out.Add(lines(i + 1))
            out.Add(lines(i + 2)) : out.Add(lines(i + 3))
            i += 4 : foundEntities = True
            Exit Do
        End If
        out.Add(lines(i))
        i += 1
    Loop

    If foundEntities Then
        ' ── Filter entity blocks ──────────────────────────────────
        Do While i < lines.Length
            If i + 1 >= lines.Length Then Exit Do

            Dim gc As String = lines(i).Trim()
            If gc <> "0" Then i += 2 : Continue Do  ' skip malformed pair

            Dim entityType As String = lines(i + 1).Trim().ToUpper()
            If entityType = "ENDSEC" Then
                out.Add(lines(i)) : out.Add(lines(i + 1))
                i += 2 : Exit Do
            End If

            ' Collect entity block as group-code/value pairs
            Dim block As New System.Collections.Generic.List(Of String)
            block.Add(lines(i)) : block.Add(lines(i + 1))
            i += 2
            Do While i + 1 < lines.Length
                If lines(i).Trim() = "0" Then Exit Do
                block.Add(lines(i)) : block.Add(lines(i + 1))
                i += 2
            Loop

            ' Find layer name at group code 8 (search group-code slots: 0, 2, 4, ...)
            Dim layerName As String = ""
            Dim layerValIdx As Integer = -1
            Dim j As Integer = 0
            Do While j + 1 < block.Count
                If block(j).Trim() = "8" Then
                    layerName = block(j + 1).Trim() : layerValIdx = j + 1 : Exit Do
                End If
                j += 2
            Loop

            ' Apply whitelist
            ' DXF spec: omitted group code 8 defaults to layer 0 -- keep as-is.
            Dim ln As String = layerName.ToUpper()
            If layerValIdx = -1 OrElse ln = "0" Then
                out.AddRange(block)
            ElseIf ln = "IV_OUTER_PROFILE" OrElse ln = "IV_INTERIOR_PROFILES" Then
                block(layerValIdx) = "0"
                out.AddRange(block)
            ElseIf (ln = "IV_BEND" OrElse ln = "IV_BEND_DOWN") AndAlso includeBendLines Then
                out.AddRange(block)
            End If
            ' else: drop -- IV_ARC_CENTERS, IV_TANGENT, any other unrecognised layer
        Loop
    End If

    ' ── Pass through OBJECTS, EOF, and anything else after ENTITIES ──
    Do While i < lines.Length
        out.Add(lines(i))
        i += 1
    Loop

    System.IO.File.WriteAllLines(filePath, out.ToArray())
End Sub

Function SanitizeForFilename(s As String) As String
    Dim result As String = s
    For Each c As Char In System.IO.Path.GetInvalidFileNameChars()
        result = result.Replace(c.ToString(), "_")
    Next
    Return result.Replace(" ", "_")
End Function

Function FormatThickness(mm As Double) As String
    If mm = 0 Then Return "0"
    If mm = Math.Floor(mm) Then Return CInt(mm).ToString()
    Return mm.ToString("0.##")
End Function

Sub ShowError(msg As String)
    Dim ef As New System.Windows.Forms.Form
    ef.Text = "PPM - Greska / Error"
    ef.Size = New System.Drawing.Size(460, 200)
    ef.StartPosition = System.Windows.Forms.FormStartPosition.CenterScreen
    ef.FormBorderStyle = System.Windows.Forms.FormBorderStyle.FixedDialog
    ef.BackColor = System.Drawing.Color.FromArgb(59, 68, 83)
    ef.MaximizeBox = False
    ef.AutoScaleMode = System.Windows.Forms.AutoScaleMode.None
    Dim lbl As New System.Windows.Forms.Label
    lbl.Text = msg : lbl.Font = New System.Drawing.Font("Segoe UI", 9)
    lbl.ForeColor = System.Drawing.Color.FromArgb(210, 153, 34)
    lbl.Location = New System.Drawing.Point(20, 20) : lbl.Size = New System.Drawing.Size(400, 60)
    ef.Controls.Add(lbl)
    Dim btn As New System.Windows.Forms.Button
    btn.Text = "OK" : btn.Font = New System.Drawing.Font("Segoe UI", 9, System.Drawing.FontStyle.Bold)
    btn.BackColor = System.Drawing.Color.FromArgb(46, 125, 209)
    btn.ForeColor = System.Drawing.Color.FromArgb(230, 237, 243)
    btn.FlatStyle = System.Windows.Forms.FlatStyle.Flat
    btn.Location = New System.Drawing.Point(180, 134) : btn.Size = New System.Drawing.Size(100, 32)
    btn.DialogResult = System.Windows.Forms.DialogResult.OK
    ef.Controls.Add(btn) : ef.AcceptButton = btn : ef.ShowDialog()
End Sub

Sub ShowSummary(nExp As Integer, nSkip As Integer, nFail As Integer, _
                nQty1 As Integer, bomLoaded As Boolean, _
                failList As System.Collections.Generic.List(Of String), _
                missingBom As System.Collections.Generic.List(Of String), _
                destFolder As String, _
                mirMergeLog As System.Collections.Generic.List(Of String), _
                weldmentLog As System.Collections.Generic.List(Of String))

    Dim extraH As Integer = 0
    If nFail > 0 Then extraH += 110
    If missingBom.Count > 0 Then extraH += 80
    If mirMergeLog.Count > 0 Then extraH += 80
    If weldmentLog.Count > 0 Then extraH += 80

    Dim sf As New System.Windows.Forms.Form
    sf.Text = "PPM - Rezultat / Summary"
    sf.Size = New System.Drawing.Size(500, 310 + extraH)
    sf.StartPosition = System.Windows.Forms.FormStartPosition.CenterScreen
    sf.FormBorderStyle = System.Windows.Forms.FormBorderStyle.FixedDialog
    sf.BackColor = System.Drawing.Color.FromArgb(59, 68, 83) : sf.MaximizeBox = False
    sf.AutoScaleMode = System.Windows.Forms.AutoScaleMode.None

    Dim y As Integer = 18

    Dim add As Action(Of System.Windows.Forms.Control) = Sub(c) sf.Controls.Add(c)

    Dim lblT As New System.Windows.Forms.Label
    lblT.Text = "EXPORT ZAVRSEN / EXPORT COMPLETE"
    lblT.Font = New System.Drawing.Font("Segoe UI", 10, System.Drawing.FontStyle.Bold)
    lblT.ForeColor = System.Drawing.Color.FromArgb(46, 125, 209)
    lblT.Location = New System.Drawing.Point(20, y) : lblT.Size = New System.Drawing.Size(460, 22)
    add(lblT) : y += 36

    Dim mkLbl As Func(Of String, System.Drawing.Color, Boolean, System.Windows.Forms.Label) =
        Function(txt, col, bold)
            Dim l As New System.Windows.Forms.Label
            l.Text = txt
            l.Font = New System.Drawing.Font("Segoe UI", 9,
                If(bold, System.Drawing.FontStyle.Bold, System.Drawing.FontStyle.Regular))
            l.ForeColor = col
            l.Location = New System.Drawing.Point(20, y) : l.Size = New System.Drawing.Size(460, 20)
            Return l
        End Function

    add(mkLbl("Izvezeno / Exported:    " & nExp,
        System.Drawing.Color.FromArgb(63, 185, 80), True)) : y += 24
    add(mkLbl("Preskoceno / Skipped:  " & nSkip & "  (nije izmenjeno)",
        System.Drawing.Color.FromArgb(180, 190, 200), False)) : y += 24
    add(mkLbl("Greska / Failed:          " & nFail,
        If(nFail > 0, System.Drawing.Color.FromArgb(210, 153, 34),
           System.Drawing.Color.FromArgb(180, 190, 200)), nFail > 0)) : y += 24

    Dim bomTxt As String
    Dim bomCol As System.Drawing.Color
    If Not bomLoaded Then
        bomTxt = "Kolicine / Quantities:  sve=1 (BOM nije ucitan)"
        bomCol = System.Drawing.Color.FromArgb(210, 153, 34)
    ElseIf nQty1 > 0 Then
        bomTxt = "Kolicine / Quantities:  " & nQty1 & " dela nije u BOM-u (kol=1)"
        bomCol = System.Drawing.Color.FromArgb(210, 153, 34)
    Else
        bomTxt = "Kolicine / Quantities:  sve iz BOM-a / all from BOM"
        bomCol = System.Drawing.Color.FromArgb(63, 185, 80)
    End If
    add(mkLbl(bomTxt, bomCol, False)) : y += 24

    add(mkLbl("Root folder: " & destFolder & "  →  MATERIAL\THICKNESSmm\",
        System.Drawing.Color.FromArgb(180, 190, 200), False)) : y += 28

    ' Missing BOM parts list
    If missingBom.Count > 0 Then
        Dim sepM As New System.Windows.Forms.Label
        sepM.BackColor = System.Drawing.Color.FromArgb(72, 82, 98)
        sepM.Location = New System.Drawing.Point(20, y) : sepM.Size = New System.Drawing.Size(460, 1)
        add(sepM) : y += 8
        add(mkLbl("Dela nije u BOM-u (kol=1) / Parts not in BOM (qty=1):",
            System.Drawing.Color.FromArgb(210, 153, 34), True)) : y += 20
        Dim txtM As New System.Windows.Forms.TextBox
        txtM.Multiline = True : txtM.ReadOnly = True
        txtM.ScrollBars = System.Windows.Forms.ScrollBars.Vertical
        txtM.BackColor = System.Drawing.Color.FromArgb(33, 38, 45)
        txtM.ForeColor = System.Drawing.Color.FromArgb(210, 153, 34)
        txtM.Font = New System.Drawing.Font("Consolas", 8)
        txtM.Text = String.Join(vbCrLf, missingBom.ToArray())
        txtM.Location = New System.Drawing.Point(20, y) : txtM.Size = New System.Drawing.Size(460, 50)
        add(txtM) : y += 58
    End If

    ' Mirrored parts merge log
    If mirMergeLog.Count > 0 Then
        Dim sepMir As New System.Windows.Forms.Label
        sepMir.BackColor = System.Drawing.Color.FromArgb(72, 82, 98)
        sepMir.Location = New System.Drawing.Point(20, y) : sepMir.Size = New System.Drawing.Size(460, 1)
        add(sepMir) : y += 8
        add(mkLbl("Ogledalni delovi / Mirrored parts (_MIR) — kolicine spojene / qty merged:",
            System.Drawing.Color.FromArgb(63, 185, 80), True)) : y += 20
        Dim txtMir As New System.Windows.Forms.TextBox
        txtMir.Multiline = True : txtMir.ReadOnly = True
        txtMir.ScrollBars = System.Windows.Forms.ScrollBars.Vertical
        txtMir.BackColor = System.Drawing.Color.FromArgb(33, 38, 45)
        txtMir.ForeColor = System.Drawing.Color.FromArgb(63, 185, 80)
        txtMir.Font = New System.Drawing.Font("Consolas", 8)
        txtMir.Text = String.Join(vbCrLf, mirMergeLog.ToArray())
        txtMir.Location = New System.Drawing.Point(20, y) : txtMir.Size = New System.Drawing.Size(460, 50)
        add(txtMir) : y += 58
    End If

    ' Weldment children log
    If weldmentLog.Count > 0 Then
        Dim sepW As New System.Windows.Forms.Label
        sepW.BackColor = System.Drawing.Color.FromArgb(72, 82, 98)
        sepW.Location = New System.Drawing.Point(20, y) : sepW.Size = New System.Drawing.Size(460, 1)
        add(sepW) : y += 8
        add(mkLbl("Zavareni sklopovi / Weldment children — kolicine ucitane / qty resolved:",
            System.Drawing.Color.FromArgb(46, 125, 209), True)) : y += 20
        Dim txtW As New System.Windows.Forms.TextBox
        txtW.Multiline = True : txtW.ReadOnly = True
        txtW.ScrollBars = System.Windows.Forms.ScrollBars.Vertical
        txtW.BackColor = System.Drawing.Color.FromArgb(33, 38, 45)
        txtW.ForeColor = System.Drawing.Color.FromArgb(46, 125, 209)
        txtW.Font = New System.Drawing.Font("Consolas", 8)
        txtW.Text = String.Join(vbCrLf, weldmentLog.ToArray())
        txtW.Location = New System.Drawing.Point(20, y) : txtW.Size = New System.Drawing.Size(460, 50)
        add(txtW) : y += 58
    End If

    If nFail > 0 Then
        Dim sepF As New System.Windows.Forms.Label
        sepF.BackColor = System.Drawing.Color.FromArgb(72, 82, 98)
        sepF.Location = New System.Drawing.Point(20, y) : sepF.Size = New System.Drawing.Size(460, 1)
        add(sepF) : y += 8
        add(mkLbl("Detalji gresaka / Failure details:",
            System.Drawing.Color.FromArgb(210, 153, 34), True)) : y += 20
        Dim txtF As New System.Windows.Forms.TextBox
        txtF.Multiline = True : txtF.ReadOnly = True
        txtF.ScrollBars = System.Windows.Forms.ScrollBars.Vertical
        txtF.BackColor = System.Drawing.Color.FromArgb(33, 38, 45)
        txtF.ForeColor = System.Drawing.Color.FromArgb(210, 153, 34)
        txtF.Font = New System.Drawing.Font("Consolas", 8)
        txtF.Text = String.Join(vbCrLf, failList.ToArray())
        txtF.Location = New System.Drawing.Point(20, y) : txtF.Size = New System.Drawing.Size(460, 80)
        add(txtF) : y += 88
    End If

    Dim sep As New System.Windows.Forms.Label
    sep.BackColor = System.Drawing.Color.FromArgb(72, 82, 98)
    sep.Location = New System.Drawing.Point(20, y) : sep.Size = New System.Drawing.Size(460, 1)
    add(sep) : y += 10

    Dim btnOK As New System.Windows.Forms.Button
    btnOK.Text = "OK"
    btnOK.Font = New System.Drawing.Font("Segoe UI", 9, System.Drawing.FontStyle.Bold)
    btnOK.BackColor = System.Drawing.Color.FromArgb(46, 125, 209)
    btnOK.ForeColor = System.Drawing.Color.FromArgb(230, 237, 243)
    btnOK.FlatStyle = System.Windows.Forms.FlatStyle.Flat
    btnOK.FlatAppearance.BorderColor = System.Drawing.Color.FromArgb(46, 125, 209)
    btnOK.Location = New System.Drawing.Point(190, y) : btnOK.Size = New System.Drawing.Size(120, 32)
    btnOK.DialogResult = System.Windows.Forms.DialogResult.OK
    add(btnOK) : sf.AcceptButton = btnOK : sf.ShowDialog()
End Sub
