' CONFIRMED WORKING core logic (D-657, tested on Stadler diesel/AdBlue
' tank; API corrections for AddBrowserFolder/Add already applied).
'
' UPDATE 1: grouping key fixed from DisplayName to FullFileName. This
' was already found and fixed in a separate script (D-658 -- a real
' run showed 7 genuinely different parts merged into one folder
' because DisplayName isn't reliably unique per file) but never
' ported back to this original standalone file until now. DisplayName
' is still used separately for the folder's human-readable label.
'
' UPDATE 2: added per-occurrence Suppressed / ReferenceMissing
' detection, same as PPM_NormaliseBrowserNodes -- this script had zero
' error handling and was only ever validated against a clean project;
' Winkler's real data has genuinely broken/suppressed references.
' Nothing else changed -- still single-document, non-recursive, same
' scope as originally built.
'
' NOTE: if this document already has leftover folders from earlier
' testing this session (jumbled Side Cap folder, TEST_FOLDER_A/B/C),
' close WITHOUT saving and reopen fresh before running this, so the
' "folder already exists" code path isn't exercised against stale
' test artifacts.

Dim SKIP_SINGLE_INSTANCES As Boolean = True

Dim oDoc As AssemblyDocument = ThisDoc.Document
Dim oPane As BrowserPane = oDoc.BrowserPanes.Item("Model")
Dim oDef As AssemblyComponentDefinition = oDoc.ComponentDefinition

Dim UNDO As Transaction = ThisApplication.TransactionManager.StartTransaction(oDoc, "Group By Same Part")

Dim skippedCount As Integer = 0

' Bucket occurrences by referenced FILE (FullFileName, not DisplayName
' -- see UPDATE 1 above), skipping suppressed/broken ones first.
Dim occsByFile As New Dictionary(Of String, List(Of ComponentOccurrence))
For Each oOcc As ComponentOccurrence In oDef.Occurrences
    Dim isSuppressed As Boolean = False
    Try
        isSuppressed = oOcc.Suppressed
    Catch
    End Try

    Dim isMissing As Boolean = False
    Try
        isMissing = oOcc.ReferencedDocumentDescriptor.ReferenceMissing
    Catch
    End Try

    If isSuppressed OrElse isMissing Then
        skippedCount += 1
        Continue For
    End If

    Try
        Dim key As String = oOcc.Definition.Document.FullFileName
        If Not occsByFile.ContainsKey(key) Then
            occsByFile(key) = New List(Of ComponentOccurrence)
        End If
        occsByFile(key).Add(oOcc)
    Catch
        skippedCount += 1
    End Try
Next

Dim foldersCreated As Integer = 0

For Each kvp As KeyValuePair(Of String, List(Of ComponentOccurrence)) In occsByFile
    Dim occList As List(Of ComponentOccurrence) = kvp.Value

    If SKIP_SINGLE_INSTANCES AndAlso occList.Count = 1 Then Continue For

    Try
        Dim folderLabel As String = occList(0).Definition.Document.DisplayName

        Dim oFolder As BrowserFolder = Nothing
        Dim folderExists As Boolean = True
        Try
            oFolder = oPane.TopNode.BrowserFolders.Item(folderLabel)
        Catch
            folderExists = False
        End Try

        If folderExists Then
            For Each oOcc As ComponentOccurrence In occList
                Try
                    oFolder.Add(oPane.GetBrowserNodeFromObject(oOcc))
                Catch
                End Try
            Next
        Else
            Dim oNodes As ObjectCollection = ThisApplication.TransientObjects.CreateObjectCollection
            For Each oOcc As ComponentOccurrence In occList
                oNodes.Add(oPane.GetBrowserNodeFromObject(oOcc))
            Next
            oFolder = oPane.AddBrowserFolder(folderLabel, oNodes)
            foldersCreated += 1
        End If
    Catch
        ' one bad group shouldn't stop the rest
    End Try
Next

UNDO.End()
MessageBox.Show("Done. " & foldersCreated & " folder(s) created, " & skippedCount & " occurrence(s) skipped (suppressed/broken reference).", "Group Occurrences By Same Part")
